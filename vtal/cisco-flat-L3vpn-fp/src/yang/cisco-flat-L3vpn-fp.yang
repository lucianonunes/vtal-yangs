module cisco-flat-L3vpn-fp {
  namespace "http://cisco.com/ns/nso/fp/examples/cisco-tsdn-flat-L3vpn";
  prefix cisco-flat-L3vpn-fp;

  import ietf-inet-types { prefix inet; }

  import ietf-yang-types { prefix yang; }

  import tailf-common { prefix tailf; }

  import tailf-ncs { prefix ncs; }

  import tailf-kicker { prefix kicker; }

  import custom-template-hook { prefix ct-hook; }

  import cisco-tsdn-core-fp-common { prefix tsdn-core-fp-common; }

  import lsa-utils { prefix lsa-utils; }

  description "MPLS L3VPN function pack - example";

  revision 2022-08-12 {
    description "Modified default value for iosxr-default-ned-id to cisco-iosxr-cli-7.40";
  }

  revision 2022-05-27 {
    description
      "Removed: Q-in-Q enum options under grouping subinterface-rewrite-common-grouping -> ingress -> translate";
  }

  revision 2022-05-26 {
    description
      "Modified: vlan-id range to 1..4094";
  }

  revision 2022-05-04 {
    description "Modified default value for iosxr-default-ned-id to cisco-iosxr-cli-7.39";
  }

  revision 2022-01-13 {
    description "Modified default value for iosxr-default-ned-id to cisco-iosxr-cli-7.38";
  }

  revision 2021-12-03 {
	description
	  "Removed: core-fp-common reference
	   Modified: Read dispatch-map using lsa-utils";
  }

  revision 2021-11-17 {
    description
      "Modified: default under cfp-configurations -> iosxr-default-ned-id";
  }

  revision 2021-09-30 {
    description "Added: container srv6 under flat-L3vpn -> endpoint -> vrf -> address-family";
  }

  revision 2021-08-06 {
    description
      "Added: tsdn-core-fp-common static-config-redeploy-indicator-component-augmentation
              grouping to plan component augment
       Added: tsdn-core-fp-common static-config-redeploy-indicator-component-augmentation
              grouping to plan-history component augment";
  }

  revision 2021-07-01 {
    description "Modified: type from boolean to string for l3vpn-route-policy -> color -> description";
  }

  revision 2021-06-16 {
    description "Modified: Updated operational status name and description";
  }

  revision 2021-05-28 {
    description "Added: new list extra-policy in l3vpn-route-policy
                 Added: new exclusive and description fields in l3vpn-route-policy -> color";
  }

  revision 2021-05-18 {
    description "Added: when condition under flat-L3vpn -> service-assurance-grouping
                        to hide service-assurance related configs when
                        'cisco-aa-service-assurance' package is not installed";
  }

  revision 2021-05-11 {
    description
    "Modified: augment flat-L3vpn->plan to use tsdn-core-fp-common:status-code-plan-augmentation";
   }

  revision 2021-05-10 {
    description "Modified: typedef operational-type and add AA extension enums";
  }

  revision 2021-04-30 {
    description "Added: flat-L3vpn -> service-status (oper-data) using IETF model";
  }

  revision 2021-03-25 {
    description "Added: flat-L3vpn -> service-assurance-grouping";
  }

  revision 2021-02-22 {
    description "Corrected typedef service-name regex pattern (removed extra backslash)";
  }

  revision 2021-02-15 {
    description "Modified default value for iosxr-default-ned-id to cisco-iosxr-cli-7.33";
  }

  revision 2020-12-11 {
    description "Modified default value for iosxr-default-ned-id to cisco-iosxr-cli-7.32";
  }

  revision 2020-11-16 {
    description "Added validate callpoint to service";
  }

  revision 2020-11-10 {
    description "Added: leaf sync-direction as mandatory input to error-recovery action";
  }

  revision 2020-11-05 {
    description "Added: When condition to BDI, to allow only when device is XE";
  }

  revision 2020-10-27 {
    description "Removed: BVI from l2-attachment-circuit, added by error but never used.";
  }

  revision 2020-10-26 {
    description "Added: leaf node BDI to support sub-interface for XE devices.";
  }

  revision 2020-10-21 {
    description "Modified: sr-te-grp -> export-route-policy is now not mandatory";
  }

  revision 2020-10-14 {
    description "Added: Ethernet interface for XE support under flat-L3vpn -> endpoint -> if-type
                    and flat-L3vpn -> endpoint -> ce-pe-prot -> e-bgp -> update-source -> if-type";
  }

  revision 2020-10-09 {
    description " Modified: sr-te-grp -> route-policy to export-route-policy
                  Added: sr-te-grp -> import-route-policy
                  Removed: sr-te-grp -> choice type";
  }

  revision 2020-09-01 {
    description " Added: String pattern under cisco-flat-L3vpn-fp:flat-L3vpn ->
                          endpoint -> vrf for not allowing spaces in vrf-definition";
  }

  revision 2020-08-18 {
    description " Updated: cleanup action now takes endpoint name as input rather than device as
                                          L3vpn service can have repeated devices in endpoints";
  }

  revision 2020-08-17 {
    description "
      Removed: min-elements requirement for endpoints to support transport slicing use-case.";
  }

  revision 2020-08-05 {
    description "Removed: stacked-service-enable flag
                 Removed: service redeploy-flag
                 Removed: service redeploy custom action
                 Removed: service get-modifications custom action
                 Removed: service no-op custom action
                 Removed: cfp-configurations -> local-user
                 Removed: cfp-configurations -> auto-cleanup
                 Added: Custom action internal-plan-change-handler
                 Added: Custom action update-internal-cfp-configurations
                 Added: Custom action error-recovery
                 Added: Internal plan change handler action
                 Modified: endpoint -> access-pe points to dispatch map instead of device tree
                 Modified: cleanup action points to dispatch map instead of device tree";
  }

  revision 2020-06-16 {
    description "Modified cleanup input no-networking 'default true' -> 'mandatory true'
                 Modified cleanup input device to include non-strict-leafref
                 Added tailf:confirm-text to cleanup";
  }

  revision 2020-06-10 {
    description "Added redeploy-input grouping (containing reconcile options)
                 Added uses redeploy-input to redeploy action";
  }

  revision 2020-05-08 {
    description "
     Added: mpls-deactivation under cisco-flat-L3vpn-fp:flat-L3vpn ->
            endpoint -> ce-pe-prot -> e-bgp -> ebgp-multihop";
  }

  revision 2020-05-05 {
    description "
     Added: sub-if-id under cisco-flat-L3vpn-fp:flat-L3vpn ->
            endpoint -> ce-pe-prot -> e-bgp -> update-source";
  }

  revision 2020-05-04 {
    description "
     Added: ebgp-multihop under cisco-flat-L3vpn-fp:flat-L3vpn ->
            endpoint -> ce-pe-prot -> e-bgp";
  }

  revision 2020-04-16 {
    description "
     Removed: cfp-configurations -> iosxr-nc-ned-id.
     Added: cfp-configurations -> iosxr-default-ned-id.
     Modified: access-pe is now mandatory";
  }

  revision 2020-04-15 {
    description "
      Added must for checking range of Bundle-Ether.
      Added must for checking range of BVI Interface";
  }

  revision 2020-04-13 {
    description "
      Added: status code plan augmentation grouping : status-code-plan-augmentation
      Added: status code plan component augmentation grouping : status-code-component-augmentation
      Added: augment plan with : status-code-plan-augmentation
      Added: augment plan-history with : status-code-plan-augmentation
      Added: augment plan component with : status-code-component-augmentation
      Added: augment plan-history component with : status-code-component-augmentation
      Added: status code oper data grouping : status-code-oper";
  }

  revision 2020-03-26 {
    description "Added: must check for rewrite ingress tag-choice.";
  }

  revision 2020-03-24 {
    description "
      Modified: mtu is hidden for Loopback interface.";
  }

  revision 2020-03-19 {
    description "
      Added: l3vpn-device-error-validation-enabled to check device errors for config change.";
  }

  revision 2020-03-16 {
    description "
      Removed: self-test-enabled flag & self-test related oper-data.";
  }

  revision 2020-03-08 {
    description "
      Added: rewrite -> ingress -> dot1q";
  }

  revision 2020-02-27 {
    description "Added update-source under cisco-flat-L3vpn-fp:flat-L3vpn ->
                endpoint -> ce-pe-prot -> e-bgp";
  }

  revision 2020-02-21 {
    description "
      Added: new list cisco-flat-L3vpn-fp:l3vpn-route-policy
             tailf:meta-data 'TSDN-UI' under cisco-flat-L3vpn-fp:l3vpn-route-policy
      Modified: moved cisco-flat-L3vpn-fp:flat-L3vpn -> endpoint -> sr-te-> odn to
                                                cisco-flat-L3vpn-fp:l3vpn-route-policy
      Removed: rd from cisco-flat-L3vpn-fp:flat-L3vpn -> endpoint
                                -> sr-te -> odn -> color ->{ipv4|ipv6}";
  }

  revision 2020-02-18 {
    description "
      Added: metric added under address-family for redistribute-connected";
  }

  revision 2020-02-14 {
    description "
      Removed: tunnel-route (including auto-route + static route options),
      Added: Right regex pattern for vpn-id under vrf definition";
  }

  revision 2020-02-05 {
    description "Added: cfp-configurations -> global-rd-enabled flag to
                                enable/disable global vrf RD vs BGP/VRF";
  }

  revision 2020-01-27 {
    description " self-test-enabled is defalut to false
          cfp-configurations -> self-test-enabled
          and removed tailf:hidden tsdn";
  }

  revision 2020-01-08 {
    description "
      Added: FiftyGigE, TwoHundredGigE, Bundle-Ether, FourHundredGigE,
      TwentyFiveGigE interfaces. 'must' condition for uint16 'Bundle-Ether'
      interface to check for numbers as interface ID ";
  }

  revision 2019-12-01 {
    description "Added: cfp-configurations -> stacked-service-enable presence container
                        along with servicepoint (used for change restriction check).";
  }

  revision 2019-10-31 {
    description "Updated: cfp-configurations -> auto-cleanup is now defaulted to false.";
  }

  revision 2019-10-24 {
    description "Added device under get modification actions
              request flat-L3vpn {service} action get-modifications input device";
  }

  revision 2019-09-25 {
    description "
      Added BVI Support under flat-L3vpn->endpoint";
  }

  revision 2019-09-11 {
    description "Added Get modifications under actions
                 request flat-L3vpn {service} action get-modifications";
  }

  revision 2019-07-27 {
    description "
     Added: custom-template-hook under: flat-L3vpn and flat-L3vpn->endpoint";
  }

  revision 2019-07-25 {
    description "
     removed: cfp-configurations -> iosxr-cli-ned-id.";
  }

  revision 2019-07-15 {
    description "
     Removed: flat-L3vpn -> endpoint -> pe-mask.
     Modified: flat-L3vpn -> endpoint -> pe-ip-addr is now of format: x.x.x.x/y.
     Modified: flat-L3vpn -> endpoint -> key is now 'endpoint-name'";
  }

  revision 2019-05-24 {
    description "
     Added: cfp-configurations -> iosxr-nc-ned-id.
     Added: cfp-configurations -> iosxr-cli-ned-id.";
  }

  revision 2019-05-13 {
    description "
     Removed: capability removed from under dynamic-device-mapping.";
  }

  revision 2019-05-10 {
    description "
     Added: custom redeploy action under flat-L3vpn -> action to redeploy all internal services.
     Added: redeploy action under flat-L3vpn -> endpoint -> action.
     Added: self-test action under flat-L3vpn.
     Added: flat-L3vpn -> self-test-delay to delay self-test start after specified value.
     Added: flat-L3vpn-actions -> cleanup; to cleanup l3vpn service.
     Added: cfp-configurations -> auto-cleanup; to force delete service for unreachable devices.
     Added: cfp-configurations -> local-user; NSO user defaulted to admin.
     Added: flat-L3vpn-plan; represents service state.
     Added: flat-L3vpn-oper-data; represents self-test results.
     Modified: New namespace.
     Modified: dynamic-device-mapping moved under cfp-configurations.";
  }

  revision 2019-02-05 {
    description "Initial revision.";
  }

  typedef Bgp-default-metric-range {
    type uint32 {
      range "0..4294967295";
    }
    description "Bgp default metric range";
  }

  typedef service-name {
    type string {
      pattern '[a-zA-Z0-9\-_]+';
    }
  }

  typedef vpn-id-type {
    type string {
      pattern "([a-fA-F0-9]{1,6})(:[a-fA-F0-9]{1,8})";
    }
  }

  typedef asn-ip-type {
    type string {
      pattern '(([0-9]+)|((([0-9]|[1-9][0-9]|1[0-9][0-9]|2[0-4][0-9]|25[0-5])'
        +'\.){3}([0-9]|[1-9][0-9]|1[0-9][0-9]|2[0-4][0-9]|25[0-5]))):[0-9]+';
    }
  }

  typedef address-family-type {
    type enumeration {
      enum ipv4 {
        tailf:info "IPv4 Address Family";
        description "IPv4 Address Family";
      }
      enum ipv6 {
        tailf:info "IPv6 Address Family";
        description "IPv4 Address Family";
      }
    }
    description "BGP Address family type";
  }

  typedef bgp-rt-type {
    type enumeration {
      enum import {
        description "For import";
      }
      enum export {
        description "For export";
      }
      enum both {
        description "For both import and export";
      }
    }
    description "BGP route-target type. Import from BGP YANG";
  }

  typedef as-no-type {
    type union {
      type uint32 {
        tailf:info "<1-4294967295>;;Autonomous system number";
        range "1..4294967295";
      }
      type string {
        tailf:info "<1.0-XX.YY>;;Autonomous system number";
        pattern '[0-9]+\.[0-9]+';
      }
    }
  }

  typedef operational-type {
    type enumeration {
      enum up {
        value 0;
        description
          "Operational status UP/Enabled.";
      }
      enum down {
        value 1;
        description
          "Operational status DOWN/Disabled.";
      }
      enum unknown {
        value 2;
        description
          "Operational status UNKNOWN.";
      }
      enum operational-state-degraded {
        value 3;
        description
          "Service Health is degraded due to one or more parts being monitored
          has issues.";
      }
      enum operational-state-monitor-paused {
        value 4;
        description
          "Service Assurance monitoring is paused.";
      }
      enum operational-state-monitor-initiated {
        value 5;
        description
          "Service Assurance monitoring is being initiated.";
      }
      enum operational-state-monitor-failed {
        value 6;
        description
          "Service Assurance monitoring encountered failure.";
      }
    }
    description
      "This attribute is used to determine the
       status of a particular element.";
  }

  grouping bgp-auto-discovery-parameters-grp {
    description "BGP parameters for auto-discovery";
    list vpn-target {
      key rt-value;
      tailf:info "Route Targets";
      description "Route Targets";
      leaf rt-type {
        tailf:info "Route-Target Type";
        description "Route-Target Type";
        type bgp-rt-type;
        mandatory true;
      }
      leaf rt-value {
        tailf:info "Route-Target Value";
        description "Route-Target Value";
        type asn-ip-type;
        tailf:cli-allow-range;
      }
    }
  }

  grouping sr-te-grp {
    leaf export-route-policy {
      tailf:info "Route policy definition";
      description "Route policy definition";
      type leafref {
        path "/cisco-flat-L3vpn-fp:l3vpn-route-policy/cisco-flat-L3vpn-fp:name";
      }
    }
    leaf import-route-policy {
      tailf:info "Route policy definition";
      description "Route policy definition";
      type leafref {
        path "/cisco-flat-L3vpn-fp:l3vpn-route-policy/cisco-flat-L3vpn-fp:name";
      }
    }
  }

  grouping subinterface-rewrite-common-grouping {
    container ingress {
      tailf:info "Set the tag rewriting policy for this EFP";
      description "Set the tag rewriting policy for this EFP";
      presence "true";
      choice tag-choice {
        leaf pop {
          tailf:info "Remove one or more tags";
          description "Remove one or more tags";
          type enumeration {
            enum "1" {
              tailf:info "Remove outer tag only";
            }
            enum "2" {
              tailf:info "Remove two outermost tags";
            }
          }
          mandatory true;
        }
        leaf push {
          tailf:info "Push one or more tags";
          description "Push one or more tags";
          type empty;
          mandatory true;
        }
        leaf translate {
          tailf:info "Replace tags with other tags";
          description "Replace tags with other tags";
          type enumeration {
            enum "1-to-1" {
              tailf:info "Replace the outermost tag with another tag";
            }
          }
          mandatory true;
        }
      }

      must "pop!='' or push or translate!=''" {
        error-message "Please provide at least one of the tag-choices: pop, push or translate.";
      }

      leaf dot1q {
        tailf:info "<1-4094> - Push a Dot1Q tag";
        description "<1-4094> - Push a Dot1Q tag";
        when "not(../pop)";
        mandatory true;
        type uint16 {
          tailf:info "<1-4094>;;VLAN Id to push";
          range "1..4094";
        }
      }

      leaf mode {
        type enumeration {
          enum symmetric {
            tailf:info "All rewrites must be symmetric";
          }
        }
      }
    }
  }

  grouping status-timestamp {
    leaf status {
      type operational-type;
      description
        "Operations status";
      tailf:info "Operations status";
    }
    leaf timestamp {
      type yang:date-and-time;
      description
        "Indicates the actual date and time when
         the service actually started (UP) or
         stopped (DOWN).";
      tailf:info "Indicates the actual date and time when
         the service actually started (UP) or
         stopped (DOWN).";
    }
    description
      "This grouping defines some operational
       parameters for the service.";
  }

  grouping service-status {
    container service-status {
      container ops {
        config false;
        uses status-timestamp;
        description
          "Operational service status.";
        tailf:info "Operational service status.";
      }
      description
        "Service status.";
      tailf:info "Service status.";
    }
    description
      "Service status grouping. Reused in
       vpn-node and vpn-network-access.";
  }


  // Global L3VPN Route Policy contains the RP for all colors & ip-prefix filtering
  list l3vpn-route-policy {
    tailf:info "Route policy definition";
    description "Route policy definition";
    tailf:meta-data "TSDN-UI";
    key name;
    leaf name {
       tailf:info "Route-Policy name";
       description "Route-Policy name";
       type service-name;
       tailf:cli-allow-range;
    }
    list color {
      tailf:info "SR policy color";
      description "SR policy color";
      key id;
      leaf id {
        tailf:info "<1-4294967295> - SR policy color";
        description "<1-4294967295> - SR policy color";
        type uint32 {
          range  "1..4294967295";
        }
        tailf:cli-allow-range;
      }

      container ipv4 {
        tailf:info "IPv4 ODN SR";
        description "IPv4 ODN SR";
        presence "true";
        leaf-list prefix {
          tailf:info "<A.B.C.D/prefix> - IPv4 Prefix List";
          description "<A.B.C.D/prefix> - IPv4 Prefix List";
          type tailf:ipv4-address-and-prefix-length;
        }
      }

      container ipv6 {
        tailf:info "IPv6 ODN SR";
        description "IPv6 ODN SR";
        presence "true";
        leaf-list ipv6-prefix {
          tailf:info "<X:X::X/length> - IPv6 Prefix List";
          description "<X:X::X/length> - IPv6 Prefix List";
          type tailf:ipv6-address-and-prefix-length;
        }
      }

      leaf exclusive {
        tailf:info "To stop all processing when condition is matched";
        description "To stop all processing when condition is matched";
        type boolean;
        default false;
      }

      leaf description {
        tailf:info "Description";
        description "Description";
        type string;
      }
    }

    list extra-policy {
      tailf:info "Extra policy will be applied to policy - an ordered list";
      description "Extra policy will be applied to policy - an ordered list";
      key name;
      ordered-by user;
      leaf name {
        tailf:info "Extra policy name";
        description "Extra policy name";
        type string;
      }
      leaf operation {
        tailf:info "Where extra policy will be applied to policy";
        description "Where extra policy will be applied to policy";
        type enumeration {
          enum "prepend";
          enum "append";
        }
        default "prepend";
      }
      leaf address {
        tailf:info "Under v4/v6 address";
        description "Under v4/v6 address";
        type enumeration {
          enum "ipv4";
          enum "ipv6";
          enum "both";
        }
        default "ipv4";
      }
    }
  }

  list flat-L3vpn {
    tailf:info "Flat L3VPN Configuration";
    description "Flat L3VPN Configuration";
    uses ncs:service-data;
    ncs:servicepoint "flat-L3vpn-external";

    tailf:validate "flat-L3vpn-validation" {
      tailf:dependency ".";
    }

    key "name";
    leaf name {
      tailf:info "Service Name for L3VPN";
      description "Service Name for L3VPN";
      type service-name;
      tailf:cli-allow-range;
    }

    uses ct-hook:template-hook;
    uses tsdn-core-fp-common:service-assurance-grouping {
      when "/tsdn-core-fp-common:enable-service-assurance = 'true'";
    }
    uses service-status;

    list endpoint {
      tailf:info "L3VPN End-point";
      description "L3VPN End-point";
      key "endpoint-name";

      leaf endpoint-name {
        tailf:info "Endpoint name";
        description "Endpoint name";
        type string;
        tailf:cli-allow-range;
      }

      leaf access-pe {
        tailf:info "PE device";
        description "PE device";
        type leafref {
          path "/ncs:devices/lsa-utils:lsa/lsa-utils:dispatch-map/lsa-utils:device/lsa-utils:name";
        }
        mandatory true;
      }

      uses ct-hook:template-hook;
      tailf:action error-recovery {
        tailf:actionpoint cisco-flat-L3vpn-fp-endpoint-error-recovery;
        tailf:info "Action to recover this device during create/update from a transient failures
                    like device connection issues once the device is reachable again.
                    For create/update failures, this action issues a sync on the device
                    & redeploys the service with reconcile option.";
        description "Action to recover this device during create/update from a transient failures
                    like device connection issues once the device is reachable again.
                    For create/update failures, this action issues a sync on the device
                    & redeploys the service with reconcile option.";
        input {
          leaf sync-direction {
            tailf:info "sync device with sync-from or sync-to";
            description "sync device with sync-from or sync-to";
            type enumeration {
              enum sync-from;
              enum sync-to;
            }
            mandatory true;
          }
        }
        output {
          leaf success {
            type boolean;
            mandatory true;
          }
          leaf detail {
            type string;
          }
        }
        tailf:confirm-text "########################\n" +
          "#        Warning       #\n" +
          "########################\n" +
          "You are about to recover a T-SDN service.\n" +
          "This will issue a sync on the device.\n" +
          "Are you sure you want to proceed?" {
            tailf:confirm-default false;
        }
      }

      leaf if-type {
        tailf:info "Interface Type";
        description "Interface Type";
        type enumeration {
          enum Bundle-Ether;
          enum BVI;
          enum Ethernet;
          enum FiftyGigE;
          enum FortyGigE;
          enum FourHundredGigE;
          enum GigabitEthernet;
          enum HundredGigE;
          enum Loopback;
          enum TenGigE;
          enum TwentyFiveGigE;
          enum TwoHundredGigE;
        }
        mandatory true;
      }

      leaf if-id {
        tailf:info "Interface Id";
        description "Interface Id";
        type string {
          pattern '[0-9]+(/[0-9]+)*';
        }
        mandatory true;
      }
      must "((if-type!='Loopback' and if-type!='BVI' and if-type!='Bundle-Ether') or " +
           " ((if-type='Loopback' or if-type='BVI' or if-type='Bundle-Ether')
           and (string(number(if-id))!='NaN')))" {
        error-message "Id must be a number";
      }
      must "(if-type!='Bundle-Ether') or ((if-type='Bundle-Ether')
                    and (string(number(if-id))>'0')
                    and (string(number(if-id))<'65536'))" {
          error-message "if-id must be in the range 1-65535";
      }
      must "(if-type!='BVI') or ((if-type='BVI')
                    and (string(number(if-id))>'0')
                    and (string(number(if-id))<'4294967296'))" {
          error-message "if-id must be in the range 1-4294967295";
      }

      leaf mtu {
        tailf:info "<64-65535> - Set the MTU on an interface";
        description "<64-65535> - Set the MTU on an interface";
        when "../if-type != 'Loopback'";
        type uint16 {
          tailf:info "<64-65535>;;MTU size in bytes";
          range "64..65535";
        }
      }

      leaf pe-ip-addr {
        tailf:info "<A.B.C.D/prefix> - PE IPv4 Address";
        description "<A.B.C.D/prefix> - PE IPv4 Address";
        type tailf:ipv4-address-and-prefix-length;
      }

      leaf pe-ipv6-addr {
        tailf:info "<X:X::X/length> - PE IPv6 Address";
        description "<X:X::X/length> - PE IPv6 Address";
        type tailf:ipv6-address-and-prefix-length;
      }

      must "pe-ip-addr!='' or pe-ipv6-addr!=''" {
        error-message "Please assign value for atleast one of the fields :
                       pe-ip-addr,pe-ipv6-addr.";
      }

      choice as-choice {
        leaf as-no {
          tailf:info "Autonomous Number";
          description "Autonomous Number";
          type as-no-type;
        }
        leaf as-no-from-device {
          tailf:info "Autonomous Number learned from device";
          description "Autonomous Number learned from device";
          type empty;
        }
      }

      leaf vlan-id {
        tailf:info "<1-4094> - VLAN Id";
        description "<1-4094> - VLAN Id";
        when "../if-type != 'Loopback' and ../if-type != 'BVI'";
        type int32 {
          range "1..4094";
        }
      }

      leaf BDI {
        tailf:info
          "BDI must be unique for each sub-interface on the device.
          <1-4095>;;BDI interface number";
        description
          "BDI must be unique for each sub-interface on the device.
          <1-4095>;;BDI interface number";
        when "../vlan-id and contains(/ncs:devices/lsa-utils:lsa/lsa-utils:dispatch-map/lsa-utils:device
              [lsa-utils:name=current()/../access-pe]/lsa-utils:ned-id,
              'cisco-ios-cli-')";
        type uint16 {
          range "1..4095";
        }
      }

      container ce-pe-prot {
        when "../as-no != '' or ../as-no-from-device";
        choice routing {
          case e-bgp {
            container e-bgp {
              tailf:info "eBGP Routing";
              description "eBGP Routing";
              leaf neighbor-ipv4 {
                tailf:info "<A.B.C.D> - Neighbor IPv4 Address";
                description "<A.B.C.D> - Neighbor IPv4 Address";
                type inet:ipv4-address;
              }

              leaf neighbor-ipv6 {
                tailf:info "<X:X::X> - Neighbor IPv6 Address";
                description "<X:X::X> - Neighbor IPv6 Address";
                type inet:ipv6-address;
              }

              leaf remote-as-ipv4 {
                tailf:info "Neighbor IPv4 Remote AS";
                description "Neighbor IPv4 Remote AS";
                when "../neighbor-ipv4!=''";
                type as-no-type;
                mandatory true;
              }

              leaf remote-as-ipv6 {
                tailf:info "Neighbor IPv6 Remote AS";
                description "Neighbor IPv6 Remote AS";
                when "../neighbor-ipv6!=''";
                type as-no-type;
                mandatory true;
              }

              container ebgp-multihop {
                presence "true";
                tailf:info "Allow EBGP neighbors not on directly connected networks";
                description "Allow EBGP neighbors not on directly connected networks";
                leaf ttl-value {
                  tailf:info "<1-255>;;maximum hop count";
                  description "<1-255>;;maximum hop count";
                  type uint8 {
                    tailf:info "<1-255>;;maximum hop count";
                    range "1..255";
                  }
                  mandatory true;
                }
                leaf mpls-deactivation {
                  tailf:info "Set to true to disable BGP MPLS forwarding.";
                  description "Set to true to disable BGP MPLS forwarding.";
                  type boolean;
                  default "false";
                }
              }

              container update-source {
                presence "true";
                tailf:info "Source of routing updates";
                description "Source of routing updates";

                leaf if-type {
                  when "not(contains(/ncs:devices/lsa-utils:lsa/lsa-utils:dispatch-map/lsa-utils:device
                  [lsa-utils:name=current()/../../../../access-pe]/lsa-utils:ned-id,
                  'cisco-ios-cli-')) or not(../../../../BDI)";
                  tailf:info "Interface Type";
                  description "Interface Type";
                  type enumeration {
                    enum Bundle-Ether;
                    enum Ethernet;
                    enum FiftyGigE;
                    enum FortyGigE;
                    enum FourHundredGigE;
                    enum GigabitEthernet;
                    enum HundredGigE;
                    enum Loopback;
                    enum TenGigE;
                    enum TwentyFiveGigE;
                    enum TwoHundredGigE;
                  }
                  mandatory true;
                }

                leaf if-id {
                  when "not(contains(/ncs:devices/lsa-utils:lsa/lsa-utils:dispatch-map/lsa-utils:device
                  [lsa-utils:name=current()/../../../../access-pe]/lsa-utils:ned-id,
                  'cisco-ios-cli-')) or not(../../../../BDI)";
                  tailf:info "Interface Id";
                  description "Interface Id";
                  type string {
                    pattern '[0-9]+(/[0-9]+)*';
                  }
                  mandatory true;
                }

                leaf sub-if-id {
                  when "not(contains(/ncs:devices/lsa-utils:lsa/lsa-utils:dispatch-map/lsa-utils:device
                  [lsa-utils:name=current()/../../../../access-pe]/lsa-utils:ned-id,
                  'cisco-ios-cli-')) or ../if-type != 'Loopback'";
                  tailf:info "Sub Interface Id";
                  description "Sub Interface Id";
                  type int32;
                }

                must "not(if-type) or (((if-type!='Loopback' and if-type!='Bundle-Ether') or " +
                    " ((if-type='Loopback' or if-type='Bundle-Ether')
                    and (string(number(if-id))!='NaN'))))" {
                  error-message "Id must be a number";
                }
                must "not(if-type) or (((if-type!='Bundle-Ether') or (if-type='Bundle-Ether')
                    and (string(number(if-id))>'0')
                    and (string(number(if-id))<'65536')))" {
                  error-message "if-id must be in the range 1-65535";
                }
                must "not(if-type) or (((if-type!='Loopback') or (if-type='Loopback')
                    and (string(number(if-id))>='0')
                    and (string(number(if-id))<='2147483647')))" {
                  error-message "if-id must be in the range 0-2147483647";
                }
              }
            }
          }
        }
      }

      container vrf {
        tailf:info "VRF Definition";
        description "VRF Definition";
        leaf vrf-definition {
          tailf:info "VRF Name";
          description "VRF Name";
          type string {
            pattern '[\w\-\.:,_@#%$\+=\|;]+';
          }
          mandatory true;
        }

        leaf route-distinguisher {
          tailf:info "ASN:nn or IPV4-address:nn,VPN Route Distinguisher";
          description "ASN:nn or IPV4-address:nn,VPN Route Distinguisher";
          type asn-ip-type;
        }

        leaf vpn-id {
          tailf:info "<0-ffffff>:  VPN ID, (OUI:VPN-Index) format(hex), 3 bytes OUI Part";
          description "<0-ffffff>:  VPN ID, (OUI:VPN-Index) format(hex), 3 bytes OUI Part";
          type vpn-id-type;
        }

        list address-family {
          tailf:info "Address Family";
          description "Address Family";
          key address-family;
          leaf address-family {
            type address-family-type;
          }
          leaf redistribute-connected {
            tailf:info "Redistribute Connected";
            description "Redistribute Connected";
            type empty;
          }
          leaf metric {
            tailf:info "Default metric";
            description "Default metric";
            when "../redistribute-connected";
            type Bgp-default-metric-range;
          }
          container srv6 {
            tailf:info "Associate SRv6 Policy";
            description "Associate SRv6 Policy";
            presence true;

            must "not(contains(/ncs:devices/lsa-utils:lsa/lsa-utils:dispatch-map/lsa-utils:device[lsa-utils:name=current()/../../../access-pe]/lsa-utils:ned-id, 'cisco-ios-cli-'))" {
              error-message "SRv6 not supported on XE devices";
            }

            leaf locator-name {
              tailf:info
                "SRv6 locator name, should match locators configured at a node-global level on each router";
              description
                "SRv6 locator name, should match locators configured at a node-global level on each router";
              type string {
                length 1..64;
              }
            }
          }
          uses bgp-auto-discovery-parameters-grp;
        }
      }

      container sr-te {
        tailf:info "Segment Routing Association";
        description "Segment Routing Association";
        when "../ce-pe-prot";
        presence "true";
        uses  sr-te-grp;
      }

      list l2-attachment-circuit {
        tailf:info "L2 Attachment Ciruit";
        description "L2 Attachment Ciruit";
        when "../if-type='BVI'";

        key "name";
        leaf name {
          tailf:info "L2 AC name";
          description "L2 AC name";
          type string;
          tailf:cli-allow-range;
        }

        leaf if-type {
          tailf:info "Interface Type";
          description "Interface Type";
          type enumeration {
            enum Bundle-Ether;
            enum FiftyGigE;
            enum FortyGigE;
            enum FourHundredGigE;
            enum GigabitEthernet;
            enum HundredGigE;
            enum TenGigE;
            enum TwentyFiveGigE;
            enum TwoHundredGigE;
          }
          mandatory true;
        }

        leaf if-id {
          tailf:info "Interface Id";
          description "Interface Id";
          type string {
            pattern '[0-9]+(/[0-9]+)*';
          }
          mandatory true;
        }
        must "((if-type!='Bundle-Ether') or " +
            " ((if-type='Bundle-Ether')
            and (string(number(if-id))!='NaN')))" {
          error-message "Id must be a number";
        }
        must "((if-type!='Bundle-Ether') or (if-type='Bundle-Ether')
                    and (string(number(if-id))>'0')
                    and (string(number(if-id))<'65536'))" {
          error-message "if-id must be in the range 1-65535";
        }

        leaf vlan-id {
          tailf:info "<1-4094> - VLAN Id";
          description "<1-4094> - VLAN Id";
          type int32 {
            range "1..4094";
          }
        }

        container rewrite {
          tailf:info "Tag Rewrite";
          description "Tag Rewrite";
          when "../vlan-id";
          presence "true";
          uses subinterface-rewrite-common-grouping;
        }
      }
    }

    tailf:action error-recovery {
      tailf:actionpoint cisco-flat-L3vpn-fp-service-error-recovery;
      tailf:info "Action to recover a service during create/update from a transient failures
                  like device connection issues once the device is reachable again.
                  For create/update failures, this action issues a sync on the device
                  & redeploys the service with reconcile option.";
      description "Action to recover a service during create/update from a transient failures
                  like device connection issues once the device is reachable again.
                  For create/update failures, this action issues a sync on the device
                  & redeploys the service with reconcile option.";
      input {
        leaf sync-direction {
          tailf:info "sync device with sync-from or sync-to";
          description "sync device with sync-from or sync-to";
          type enumeration {
            enum sync-from;
            enum sync-to;
          }
          mandatory true;
        }
      }
      output {
        leaf success {
          type boolean;
          mandatory true;
        }
        leaf detail {
          type string;
        }
      }
      tailf:confirm-text "########################\n" +
        "#        Warning       #\n" +
        "########################\n" +
        "You are about to recover a T-SDN service.\n" +
        "This will issue a sync on the device.\n" +
        "Are you sure you want to proceed?" {
          tailf:confirm-default false;
      }
    }

    container action {
      tailf:action self-test {
        tailf:actionpoint flat-L3vpn-self-test-actionpoint;
        input {
        }
        output {
          leaf status {
            type string;
          }
          leaf message {
            type string;
          }
        }
      }
    }
  }

  list flat-L3vpn-plan {
    config false;
    tailf:cdb-oper {
      tailf:persistent true;
    }
    key "name";
    leaf name {
      type string;
    }

    uses ncs:nano-plan-data;
    uses ncs:nano-plan-history;
  }

  container cfp-configurations {
    list dynamic-device-mapping {
      tailf:info "Dynamic Device Mapping";
      description "Dynamic Device Mapping";
      key "ned-id";
      leaf ned-id {
        tailf:info "Device NED ID, eg ned:netconf";
        description "Device NED ID, eg ned:netconf";
        type string;
        tailf:cli-allow-range;
      }
      leaf python-impl-class-name {
        tailf:info "Device Python implementation class, eg module.class";
        description "Device Python implementation class, eg module.class";
        type string;
        mandatory true;
      }
    }

    leaf l3vpn-validation-enabled {
      tailf:info "If set to true, following validations are done for l3vpn service:
                  1. All the endpoint interfaces are available on the endpoint.";
      description "If set to true, following validations are done for l3vpn service:
                  1. All the endpoint interfaces are available on the endpoint.";
      type boolean;
      default true;
    }

    leaf l3vpn-device-error-validation-enabled {
      tailf:info "If set to true, following validations are done for l3vpn service:
                  1. Check if RD change will be accepted by endpoint.";
      description "If set to true, following validations are done for l3vpn service:
                  1. Check if RD change will be accepted by endpoint.";
      type boolean;
      default true;
    }

    leaf iosxr-default-ned-id {
      tailf:info "NED ID of the default IOSXR Device.";
      description "NED ID of the default IOSXR Device.";
      tailf:hidden tsdn;
      type string;
      default "cisco-iosxr-cli-7.40:cisco-iosxr-cli-7.40";
    }

    container global-rd-enabled {
      tailf:info "Set this flag to apply RD under global VRF definition.";
      description "Set this flag to apply RD under global VRF definition.";
      presence "true";
      uses ncs:service-data;
      ncs:servicepoint "flat-L3vpn-cfp-config";
    }
  }

  container flat-L3vpn-actions {
    tailf:action cleanup {
      tailf:actionpoint cisco-flat-L3vpn-fp-cleanup;
      tailf:info "Clean up L3vpn service configuration and operational data";
      description "Clean up L3vpn service configuration and operational data";
      input {
        leaf service {
          type string;
          mandatory true;
        }
        leaf endpoint {
          tailf:info "Clean up L3vpn service configuration for a given endpoint";
          description "Clean up L3vpn service configuration for a given endpoint";
          type string;
        }
        leaf no-networking {
          type boolean;
          mandatory true;
        }
      }
      output {
        leaf success {
          type boolean;
          mandatory true;
        }
        leaf detail {
          type string;
        }
      }
      tailf:confirm-text "########################\n" +
        "#        Warning       #\n" +
        "########################\n" +
        "You are about to forcefully cleanup a T-SDN service.\n" +
        "This will affect the deploying service and leave network device(s) "
        + "& NSO out-of-sync (for no-networking=true).\n" +
        "Are you sure you want to proceed?" {
          tailf:confirm-default false;
      }
    }
    tailf:action internal-plan-change-handler {
      tailf:hidden full;
      tailf:actionpoint l3vpn-internal-plan-change-handler;
      tailf:info "Action that redeploys external service/zombie based on internal plan change.";
      description "Action that redeploys external service/zombie based on internal plan change.";
      input {
        uses kicker:action-input-params;
      }
      output {
      }
    }
    tailf:action error-recovery {
      tailf:actionpoint cisco-flat-L3vpn-fp-error-recovery;
      tailf:info "Action to recover a service during create/update/delete from a transient failures
                  like device connection issues once the device is reachable again.
                  For create/update failures, this action issues a sync on the device
                  & redeploys the service with reconcile option.
                  For delete failures, this action issues a sync on the device &
                  redeploys zombie services.";
      description "Action to recover a service during create/update/delete from a transient failures
                  like device connection issues once the device is reachable again.
                  For create/update failures, this action issues a sync on the device
                  & redeploys the service with reconcile option.
                  For delete failures, this action issues a sync on the device &
                  redeploys zombie services.";
      input {
        leaf service {
          tailf:info "Service to recover";
          description "Service to recover";
          type string;
          mandatory true;
        }
        leaf endpoint {
          tailf:info "Recover this endpoint under given service.";
          description "Recover this endpoint under given service.";
          type string;
        }
        leaf sync-direction {
          tailf:info "sync device with sync-from or sync-to";
          description "sync device with sync-from or sync-to";
          type enumeration {
            enum sync-from;
            enum sync-to;
          }
          mandatory true;
        }
      }
      output {
        leaf success {
          type boolean;
          mandatory true;
        }
        leaf detail {
          type string;
        }
      }
      tailf:confirm-text "########################\n" +
        "#        Warning       #\n" +
        "########################\n" +
        "You are about to recover a T-SDN service.\n" +
        "This will issue a sync on the device.\n" +
        "Are you sure you want to proceed?" {
          tailf:confirm-default false;
      }
    }
    tailf:action update-internal-cfp-configurations {
      tailf:hidden tsdn;
      tailf:actionpoint update-l3vpn-internal-cfp-configurations;
      tailf:info "Copy over changes in external cfp-configurations to internal cfp-configurations";
      description "Copy over changes in external cfp-configurations to internal cfp-configurations";
      input {
      }
      output {
      }
    }
  }

  augment /flat-L3vpn-plan/plan {
    uses tsdn-core-fp-common:status-code-plan-augmentation;
  }

  augment /flat-L3vpn-plan/plan-history {
    uses tsdn-core-fp-common:status-code-plan-augmentation;
  }

  augment /flat-L3vpn-plan/plan/component {
    uses tsdn-core-fp-common:status-code-component-augmentation;
    uses tsdn-core-fp-common:static-config-redeploy-indicator-component-augmentation;
  }

  augment /flat-L3vpn-plan/plan-history/plan/component {
    uses tsdn-core-fp-common:status-code-component-augmentation;
    uses tsdn-core-fp-common:static-config-redeploy-indicator-component-augmentation;
  }
}
