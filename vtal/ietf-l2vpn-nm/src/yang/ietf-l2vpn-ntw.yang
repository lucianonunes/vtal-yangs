module ietf-l2vpn-ntw {
  yang-version 1.1;
  namespace "urn:ietf:params:xml:ns:yang:ietf-l2vpn-ntw";
  prefix l2vpn-ntw;

  // NSO ADDITION START
  import custom-template-hook { prefix ct-hook; }
  import tailf-kicker { prefix kicker; }
  import tailf-common { prefix tailf; }
  import tailf-ncs { prefix ncs; }
  import cisco-flat-L2vpn-fp { prefix cisco-flat-L2vpn-fp; }
  import cisco-tsdn-core-fp-common { prefix tsdn-core-fp-common; }
  import lsa-utils { prefix lsa-utils; }
  import ietf-routing-types { prefix rt-types; }
  // NSO ADDITION END

  import ietf-inet-types {
    prefix inet;
    reference
      "Section 4 of RFC 6991";
  }
  import ietf-yang-types {
    prefix yang;
    reference
      "Section 3 of RFC 6991";
  }
  import ietf-packet-fields {
    prefix packet-fields;
    reference
      "RFC 8519 - YANG Data Model for Network Access Control
                  Lists (ACLs).";
  }
  import ietf-vpn-common {
    prefix vpn-common;
    reference
     "RFC XXX: YANG Data Model for VPNs types.";
  }

  // NSO ADDITION START
  import resource-allocator {
    prefix ralloc;
  }
  import id-allocator {
    prefix idalloc;
  }
  // NSO ADDITION END

  organization
    "IETF OPSA (Operations and Management Area) Working Group";
  contact
    "WG Web:   <http://tools.ietf.org/wg/opsawg/>
        WG List:  <mailto:opsawg@ietf.org>
        Editor:    Samier Barguil
                  <mailto:samier.barguilgiraldo.ext@telefonica.com>
        Editor:    Oscar Gonzalez de Dios
                  <mailto:oscar.gonzalezdedios@telefonica.com>
        Author:    Mohamed Boucadair
                  <mailto:mohamed.boucadair@orange.com>
        Author:    Luis Angel Munoz
                  <mailto:luis-angel.munoz@vodafone.com>
        Author:    Luay Jalil
                  <mailto:luay.jalil@verizon.com>
        Author:    Jichun Ma
                  <mailto:majc16@chinaunicom.cn>
    ";
  description
    "The YANG module defines a generic network configuration
     model for Layer 2 VPN services common across all of the
     vendor implementations.

     Copyright (c) 2020 IETF Trust and the persons identified as
     authors of the code.  All rights reserved.

     Redistribution and use in source and binary forms, with or
     without modification, is permitted pursuant to, and subject to
     the license terms contained in, the Simplified BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.";

  revision 2022-06-10 {
    description "
        Added: pattern under l2vpn-ntw -> vpn-services -> vpn-service -> vpn-nodes
                   -> vpn-node -> multi-home -> esi-value -> string
        Modified: tailf:info under l2vpn-ntw -> vpn-services -> vpn-service -> vpn-nodes
                   -> vpn-node -> multi-home -> esi-value -> string
        Modified: destription under l2vpn-ntw -> vpn-services -> vpn-service -> vpn-nodes -> vpn-node
                   -> vpn-network-accesses -> vpn-network-access -> connection -> dot1q-interface -> dot1q";
  }

  revision 2022-05-27 {
    description
      "Removed: Q-in-Q enum options under grouping subinterface-rewrite-common-grouping -> ingress -> translate";
  }

  revision 2022-05-10 {
    description
      "Added: leaf enable under l2vpn-ntw -> vpn-services -> vpn-service -> vpn-nodes -> vpn-node
              -> vpn-network-accesses -> vpn-network-access -> connection -> split-horizon
       Removed: presence statement under l2vpn-ntw -> vpn-services -> vpn-service -> vpn-nodes -> vpn-node
                -> vpn-network-accesses -> vpn-network-access -> connection -> split-horizon";
  }

  revision 2022-03-10 {
    description
      "Modified: when condition under l2vpn-ntw -> vpn-services -> vpn-service -> evi-source-choice
       Modified: when condition under l2vpn-ntw -> vpn-services -> vpn-service -> evi-target-choice";
  }

  revision 2022-03-09 {
    description
    "Added: presence statement from vpn-services -> vpn-service -> vpn-target";
  }

  revision 2022-02-15 {
    description
      "Added: EVPN Multipoint Support
       Added: identity evpn-pbb
       Added: leaf svc-topo under vpn-services -> vpn-service
       Added: container vpn-target under vpn-services -> vpn-service
       Added: when condition under te-service-mapping -> te-mapping -> te -> sr-policy
       Modified: must condition under te-service-mapping -> te-mapping -> te -> odn
       Added: leaf node-role  under vpn-services -> vpn-service -> vpn-nodes -> vpn-node
       Added: leaf mac-learning-mode under vpn-services -> vpn-service -> vpn-nodes -> vpn-node
              -> signaling-options -> evpn-bgp
       Added: uses vpn-common:vpn-route-targets under vpn-services -> vpn-service -> vpn-nodes
              -> vpn-node -> signaling-options -> evpn-bgp
       Added: container split-horizon under vpn-services -> vpn-service -> vpn-nodes -> vpn-node
              -> vpn-network-accesses -> vpn-network-access -> connection
       Added: when condition under vpn-services -> vpn-service -> vpn-nodes -> vpn-node
              -> vpn-network-accesses -> vpn-network-access -> ethernet-service-oam";
  }

  revision 2022-01-12 {
    description
      "Removed: policy-type under te-service-mapping -> te-mapping -> te -> sr-policy";
  }

  revision 2021-12-03 {
    description
      "Added: policy-type under te-service-mapping -> te-mapping -> sr-policy -> policy-type";
  }

  revision 2021-12-03 {
	description
	  "Removed: core-fp-common reference
	   Modified: Read dispatch-map using lsa-utils";
  }

  revision 2021-10-01 {
    description
      "Modified: tailf:info for sr-policy and odn";
  }

  revision 2021-09-24 {
    description
      "Modified: tailf:info for Interface-mtu";
  }

  revision 2021-09-17 {
    description
      "Added: input leaf vpn-node for l2nm-actions -> cleanup action";
  }

  revision 2021-08-05 {
    description
      "Modified: Changed evpn-bgp, t-ldp-pwe, dot1q-interface, dot1q, untagged-interface, untagged to presence containers";
  }

  revision 2021-07-30 {
    description
      "Added: tsdn-core-fp-common static-config-redeploy-indicator-component-augmentation grouping to plan component augment
       Added: tsdn-core-fp-common static-config-redeploy-indicator-component-augmentation grouping to plan-history component augment";
  }

  revision 2021-07-27 {
    description
      "Modified: Moved the augmentations for nodes to in-line yang model";
  }

  revision 2021-06-25 {
    description
      "Removed: list y-1731-profile under vpn-network-accesses -> vpn-network-access -> ethernet-service-oam
                -> y-1731";
  }

  revision 2021-05-28 {
    description
      "Added: leaf version under under vpn-network-accesses -> vpn-network-access ->
                ethernet-service-oam -> y-1731 -> y-1731-profile -> delay-params";
  }

  revision 2021-05-27 {
    description
      "Removed: leaf loss-measurement under vpn-network-accesses -> vpn-network-access ->
                ethernet-service-oam -> y-1731 -> y-1731-profile
       Removed: leaf synthetic-loss-measurement under vpn-network-accesses -> vpn-network-access ->
                ethernet-service-oam -> y-1731 -> y-1731-profile
       Removed: container delay-measurement under vpn-network-accesses -> vpn-network-access ->
                ethernet-service-oam -> y-1731 -> y-1731-profile
       Added: container delay-params under vpn-network-accesses -> vpn-network-access ->
              ethernet-service-oam -> y-1731 -> y-1731-profile
       Added: container loss-params under vpn-network-accesses -> vpn-network-access ->
              ethernet-service-oam -> y-1731 -> y-1731-profile";
  }

  revision 2021-05-25 {
    description
      "Added: leaf priority under vpn-services -> vpn-service -> vpn-nodes -> vpn-node ->
              vpn-network-accesses -> vpn-network-access -> ethernet-service-oam ->
              y-1731 -> y-1731-profile";
  }

  revision 2021-05-18 {
    description
      "Removed: 'uses tsdn-core-fp-common:service-assurance-grouping'
                 under vpn-services -> vpn-service";
  }

  revision 2021-05-13 {
    description
    "Modified: uint32 range of vpn-network-accesses -> vpn-network-access ->
               ethernet-service-oam -> y-1731 -> y-1731-profile -> message-period
     Added: must condition under vpn-network-accesses -> vpn-network-access ->
            ethernet-service-oam -> y-1731 -> y-1731-profile ";
  }

  revision 2021-05-07 {
    description
    "Modified: augment l2vpn->plan to use tsdn-core-fp-common:status-code-plan-augmentation";
  }

  revision 2021-04-30 {
    description "Allowed: vpn-services -> vpn-service -> service-status (oper-data)";
  }

  revision 2021-03-25 {
    description "Allowed: vpn-services -> vpn-service -> vpn-nodes -> vpn-node ->
                          vpn-network-accesses -> vpn-network-access -> ethernet-service-oam ->
                          y-1731
                 Added: vpn-services -> vpn-service -> vpn-nodes -> vpn-node ->
                        vpn-network-accesses -> vpn-network-access -> ethernet-service-oam ->
                        y-1731 -> y-1731-profile
                 Added: vpn-services -> vpn-service -> service-assurance-grouping";
  }

  revision 2021-02-15 {
    description "Modified: tailf:info for signaling-options, ac-pw-list, and vpn-network-access";
  }

  revision 2021-02-15 {
    description "Removed: Unused groupings;";
  }

  revision 2021-01-27 {
    description "Removed: Unused elements containing tailf:hidden full";
  }

  revision 2020-12-07 {
    description "Added evi-id-choice choice under vpn-service
                 Added evi-source-choice choice under vpn-service
                 Added evi-target-choice choice under vpn-service
                 Removed mandatory condition from l2vpn-ntw ip-pools evi-id-pool-name and
                   evi-source-target-pool-name";
  }

  revision 2020-11-16 {
    description "Added untagged-interface container under vpn-service->vpn-node->vpn-network-access->connection
                 Added validate callpoint to service";
  }

  revision 2020-11-10 {
    description "Added leaf sync-direction as mandatory input to error-recovery action";
  }

  revision 2020-11-06 {
      description "Added: vpn-node -> te-service-mapping -> te-mapping -> odn";
  }

  revision 2020-10-19 {
      description "1. Removed choice policy-type and groupings sr-te-pref-path-grp, rsvp-tunnel-te-pref-path-grp and added te-service-mapping instead to match naming with IETF standard models
      2. Added container evi-allocation-data oper-data, leaf control-word, container multi-home, container rewrite, grouping subinterface-rewrite-common-grouping
      3. Unhide Interface-mtu";
  }

  revision 2020-10-13 {
      description "Added mpls-label leaf";
  }

  revision 2020-10-05 {
    description "Added: choice policy-type,
      groupings rsvp-tunnel-te-pref-path-grp and sr-te-pref-path-grp";
  }

  revision 2020-05-26 {
    description
      "Third revision -02 version";
    reference
      "RFC XXXX: A Layer 2 VPN Network YANG Model.";
  }

  /* Features */

 feature multicast-like {
    description
      "Indicates the support of multicast-like capabilities
       in a L2VPN.";
  }

  feature extranet-vpn {
    description
      "Indicates the Support of Extranet VPN.";
  }

  feature target-sites {
    description
      "Indicates the support of 'target-sites' match flow
       parameter.";
  }

  feature l2cp-control {
    description
      "Indicates the support of L2CP control.";
  }

  feature input-bw {
    description
      "Indicates the suppport of Input Bandwidth
      in a VPN.";
  }

  feature output-bw {
    description
      "Indicates the support of Output Bandwidth in
       a VPN";
  }

  feature uni-list {
    description
      "Indicates thesupport of UNI list in a VPN.";
  }

  feature cloud-access {
    description
      "Indicates the support of a VPN to connect to a Cloud Service
       provider.";
  }

  feature oam-3ah {
    description
      "Indicates the support of OAM 802.3ah.";
  }

  feature micro-bfd {
    description
      "Indicates the support of Micro-BFD.";
  }

  feature bfd {
    description
      "Indicates the support of BFD.";
  }

  feature signaling-options {
    description
      "Indicates the support of signalling option.";
  }

  feature site-diversity {
    description
      "Indicates the support of site diversity constraints in
       a VPN.";
  }

  feature encryption {
    description
      "Indicates the support of encryption.";
  }

  feature always-on {
    description
      "Indicates the support for always-on access
       constraint.";
  }

  feature requested-type {
    description
      "Indicates the support for requested-type access
       constraint.";
  }

  feature bearer-reference {
    description
      "Indicates the support for bearer-reference access
       constraint.";
  }

  feature lag-interface {
    description
      "Enable lag-interface.";
  }

  feature vlan {
    description
      "Indicates the support of VLAN.";
  }

  feature dot1q {
    description
      "Indicates the support of Dot1Q.";
  }

  feature sub-inf {
    description
      "Indicates the support of Sub Interface.";
  }

  feature qinq {
    description
      "Indicates the support of QinQ.";
  }

  feature qinany {
    description
      "Indicates the support of QinAny.";
  }

  feature atm {
    description
      "Indicates the support of ATM.";
  }

  feature vxlan {
    description
      "Indicates the support of VxLAN.";
  }

  feature ipv4 {
    description
      "Indicates the support in a VPN.";
  }

  feature ipv6 {
    description
      "Indicates the support in a VPN.";
  }

  feature lan-tag {
    description
      "Indicates the LAN Tag support in a VPN.";
  }

  /* Typedefs */


  typedef operational-type {
    type enumeration {
      enum up {
        value 0;
        description
          "Operational status UP.";
      }
      enum down {
        value 1;
        description
          "Operational status DOWN";
      }
      enum unknown {
        value 2;
        description
          "Operational status UNKNOWN";
      }
    }
    description
      "This is an attribute used to determine the
       operational status of a particular element.";
  }

  typedef svc-id {
    type string;
    description
      "Indicates the type of service component identifier.";
  }

  typedef ccm-priority-type {
    type uint8 {
      range "0..7";
    }
    description
      "A 3 bit priority value to be used in the VLAN tag,
       if present in the transmitted frame.";
  }

  typedef control-mode {
    type enumeration {
      enum peer {
        description
          "Peer mode, i.e., participate in the protocol towards
           the CE. Peering is common for LACP  and E-LMI and
           occasionally for LLDP. For virtual private services
           the Subscriber can also request that the Service
           Provider peer spanning tree.";
      }
      enum tunnel {
        description
          "Tunnel mode,i.e.,pass to the egress or destination site.
           For EPL, the expectation is that L2CP frames are
           tunneled.";
      }
      enum discard {
        description
          "Discard mode,i.e.,discard the frame.";
      }
    }
    description
      "Defining a type of the control mode on L2CP protocols.";
  }

  typedef neg-mode {
    type enumeration {
      enum full-duplex {
        description
          "Defining Full duplex mode";
      }
      enum auto-neg {
        description
          "Defining Auto negotiation mode";
      }
    }
    description
      "Defining a type of the negotiation mode";
  }

  /* Identities */

  identity mapping-type {
    base vpn-common:multicast-gp-address-mapping;
    description
      "Identity mapping-type.";
  }

  identity protection-mode {
    description
      "Identity of protection mode";
  }

  identity oneplusone {
    base protection-mode;
    description
      "In this scheme, the primary circuit will be
       protected by a backup circuit, typically meeting certain
       diverse path/fiber/site/node criteria.  Both primary and
       protection circuits are provisioned to be in the active
       forward ing state. The subscriber may choose to send the
       same service frames across both circuits simultaneously.";
  }

  identity one-to-one {
    base protection-mode;
    description
      "In this scheme, a backup circuit to the primary
       circuit is provisioned.  Depending on the implementation
       agreement, the protection circuits may either always be
       in active forwarding state, or may only become active when
       a faulty state is detected on the primary circuit.";
  }


  identity bundling-type {
    description
      "The base identity for the bundling type.  It supports
       multiple CE-VLANs associated with an L2VPN service or
       all CE-VLANs associated with an L2VPN service.";
  }

  identity multi-svc-bundling {
    base bundling-type;
    description
      "Identity for multi-service bundling, i.e.,
       multiple CE-VLAN IDs can be associated with an
       L2VPN service at a site.";
  }

  identity one2one-bundling {
    base bundling-type;
    description
      "Identity for one-to-one service bundling, i.e.,
       each L2VPN can be associated with only one CE-VLAN ID
       at a site.";
  }

  identity all2one-bundling {
    base bundling-type;
    description
      "Identity for all-to-one bundling, i.e., all CE-VLAN IDs
       are mapped to one L2VPN service.";
  }

  identity color-id {
    description
      "Base identity of the color ID.";
  }

  identity color-id-cvlan {
    base color-id;
    description
      "Identity of the color ID based on a CVLAN.";
  }

  identity color-type {
    description
      "Identity of color types.";
  }

  identity green {
    base color-type;
    description
      "Identity of the 'green' color type.";
  }

  identity yellow {
    base color-type;
    description
      "Identity of the 'yellow' color type.";
  }

  identity red {
    base color-type;
    description
      "Identity of the 'red' color type.";
  }

  identity perf-tier-opt {
    description
      "Identity of performance tier option.";
  }

  identity metro {
    base perf-tier-opt;
    description
      "Identity of metro";
  }

  identity regional {
    base perf-tier-opt;
    description
      "Identity of regional";
  }

  identity continental {
    base perf-tier-opt;
    description
      "Identity of continental";
  }

  identity global {
    base perf-tier-opt;
    description
      "Identity of global";
  }

  identity policing {
    description
      "Identity of policing type";
  }

  identity one-rate-two-color {
    base policing;
    description
      "Identity of one-rate, two-color (1R2C)";
  }

  identity two-rate-three-color {
    base policing;
    description
      "Identity of two-rate, three-color (2R3C)";
  }


  identity loop-prevention-type {
    description
      "Identity of loop prevention.";
  }

  identity shut {
    base loop-prevention-type;
    description
      "Identity of shut protection.";
  }

  identity trap {
    base loop-prevention-type;
    description
      "Identity of trap protection.";
  }

  identity t-ldp-pwe-type {
    description
      "Identity for t-ldp-pwe-type.";
  }

  identity vpws-type {
    base t-ldp-pwe-type;
    description
      "Identity for VPWS";
  }

  identity vpls-type {
    base t-ldp-pwe-type;
    description
      "Identity for vpls";
  }

  identity hvpls {
    base t-ldp-pwe-type;
    description
      "Identity for h-vpls";
  }

  identity l2vpn-type {
    description
      "Layer 2 VPN types";
  }

  identity l2vpn-vpws {
    base l2vpn-type;
    description
      "VPWS L2VPN type.";
  }

  identity l2vpn-vpls {
    base l2vpn-type;
    description
      "VPLS L2VPN type.";
  }

  identity distribute-vpls {
    base l2vpn-type;
    description
      "distribute VPLS L2VPN type.";
  }

  identity evpn-type {
    description
      "Ethernet VPN types";
  }

  identity evpn-vpws {
    base evpn-type;
    description
      "VPWS support in EVPN.";
  }

  identity evpn-pbb {
    base evpn-type;
    description
      " Provider Backbone Bridging Support in EVPN.";
  }

  identity pm-type {
    description
      "Performance-monitoring type.";
  }

  identity loss {
    base pm-type;
    description
      "Loss measurement.";
  }

  identity delay {
    base pm-type;
    description
      "Delay measurement.";
  }

  identity placement-diversity {
    description
      "Base identity for site placement constraints.";
  }

  identity bearer-diverse {
    base placement-diversity;
    description
      "Identity for bearer diversity.
       The bearers should not use common elements.";
  }

  identity pe-diverse {
    base placement-diversity;
    description
      "Identity for PE diversity.";
  }

  identity pop-diverse {
    base placement-diversity;
    description
      "Identity for POP diversity.";
  }

  identity linecard-diverse {
    base placement-diversity;
    description
      "Identity for linecard diversity.";
  }

  identity same-pe {
    base placement-diversity;
    description
      "Identity for having sites connected on the same PE.";
  }

  identity same-bearer {
    base placement-diversity;
    description
      "Identity for having sites connected using the same bearer.";
  }

  identity mac-learning-mode {
    description
      "MAC learning mode.";
  }

  // identity data-plane {
  //   base mac-learning-mode;
  //   description
  //     "User MAC addresses are learned through ARP broadcast.";
  // }

  identity control-plane {
    base mac-learning-mode;
    description
      "User MAC addresses are advertised through EVPN-BGP.";
  }

  identity mac-action {
    description
      "Base identity for a MAC action.";
  }

  identity drop {
    base mac-action;
    description
      "Identity for dropping a packet.";
  }

  identity flood {
    base mac-action;
    description
      "Identity for packet flooding.";
  }

  identity warning {
    base mac-action;
    description
      "Identity for sending a warning log message.";
  }

  identity load-balance-method {
    description
      "Base identity for load balance method.";
  }

  identity fat-pw {
    base load-balance-method;
    description
      "Identity for Fat PW. Fat label is
       applied to Pseudowires across MPLS
       network.";
  }

  identity entropy-label {
    base load-balance-method;
    description
      "Identity for entropy label.Entropy label
       is applied to IP forwarding,
       L2VPN or L3VPN across MPLS network";
  }

  identity vxlan-source-port {
    base load-balance-method;
    description
      "Identity for vxlan source port.VxLAN
       Source Port is one load balancing method.";
  }

  identity precedence-type {
    description
      "Redundancy type. The service can be created
       with active and bakcup signalization.";
  }

  identity primary {
    base precedence-type;
    description
      "Identifies the Main L2VPN.";
  }

  identity backup {
    base precedence-type;
    description
      "Identifies the Backup L2VPN.";
  }

  /* Groupings */
  // NSO-REMOVED START
  // grouping ports {
  //   choice source-port {
  //     container source-port-range-or-operator {
  //       uses packet-fields:port-range-or-operator;
  //       description
  //         "Source port definition.";
  //     }
  //     description
  //       "Choice of specifying the source port or referring to
  //        a group of source port numbers.";
  //   }
  //   choice destination-port {
  //     container destination-port-range-or-operator {
  //       uses packet-fields:port-range-or-operator;
  //       description
  //         "Destination port definition.";
  //     }
  //     description
  //       "Choice of specifying a destination port or referring
  //        to a group of destination port numbers.";
  //   }
  //   description
  //     "Choice of specifying a source or destination port numbers.";
  // }
  // NSO-REMOVED END

  // NSO-REMOVED START
  // grouping cfm-802-grouping {
  //   leaf maid {
  //     type string;
  //     description
  //       "MA ID";
  //   }
  //   leaf mep-id {
  //     type uint32;
  //     description
  //       "Local MEP ID";
  //   }
  //   leaf mep-level {
  //     type uint32;
  //     description
  //       "MEP level";
  //   }
  //   leaf mep-up-down {
  //     type enumeration {
  //       enum up {
  //         description
  //           "MEP up";
  //       }
  //       enum down {
  //         description
  //           "MEP down";
  //       }
  //     }
  //     description
  //       "MEP up/down";
  //   }
  //   leaf remote-mep-id {
  //     type uint32;
  //     description
  //       "Remote MEP ID";
  //   }
  //   leaf cos-for-cfm-pdus {
  //     type uint32;
  //     description
  //       "COS for CFM PDUs";
  //   }
  //   leaf ccm-interval {
  //     type uint32;
  //     description
  //       "CCM interval";
  //   }
  //   leaf ccm-holdtime {
  //     type uint32;
  //     description
  //       "CCM hold time";
  //   }
  //   leaf ccm-p-bits-pri {
  //     type ccm-priority-type;
  //     description
  //       "The priority parameter for CCMs transmitted by the MEP";
  //   }
  //   description
  //     "Grouping for 802.1ag CFM attribute";
  // }
  // NSO-REMOVED END

  grouping y-1731 {
    list y-1731 {
      key "maid";
      leaf maid {
        type string;
        description
          "MA ID ";
        tailf:info "MA ID ";
      }
      leaf mep-id {
        type uint32;
        description
          "Local MEP ID";
        tailf:info "Local MEP ID";
      }
  // NSO-REMOVED START
  //     leaf type {
  //       type identityref {
  //         base pm-type;
  //       }
  //       description
  //         "Performance monitor types";
  //     }
  //     leaf remote-mep-id {
  //       type uint32;
  //       description
  //         "Remote MEP ID";
  //     }
  // NSO-REMOVED END
      leaf message-period {
        type uint32;
        description
          "Defines the interval between OAM messages. The message
           period is expressed in milliseconds";
        tailf:info "Defines the interval between OAM messages. The message
                    period is expressed in 3.3ms|10ms|100ms|1s|10s|1m|10m";
      }
  // NSO-REMOVED START
  //     leaf measurement-interval {
  //       type uint32;
  //       description
  //         "Specifies the measurement interval for statistics. The
  //          measurement interval is expressed in seconds";
  //     }
  //     leaf cos {
  //       type uint32;
  //       description
  //         "Class of service";
  //     }
  //     leaf loss-measurement {
  //       type boolean;
  //       description
  //         "Whether enable loss measurement";
  //     }
  //     leaf synthetic-loss-measurement {
  //       type boolean;
  //       description
  //         "Indicate whether enable synthetic loss measurement";
  //     }
  //     container delay-measurement {
  //       leaf enable-dm {
  //         type boolean;
  //         description
  //           "Whether to enable delay measurement";
  //       }
  //       leaf two-way {
  //         type boolean;
  //         description
  //           "Whether delay measurement is two-way (true) of one-
  //            way (false)";
  //       }
  //       description
  //         "Container for delay measurement";
  //     }
  //     leaf frame-size {
  //       type uint32;
  //       description
  //         "Frame size";
  //     }
  //     leaf session-type {
  //       type enumeration {
  //         enum proactive {
  //           description
  //             "Proactive mode";
  //         }
  //         enum on-demand {
  //           description
  //             "On demand mode";
  //         }
  //       }
  //       description
  //         "Session type";
  //     }
  // NSO-REMOVED END
      description
        "List for y-1731.";
      tailf:info "List for y-1731.";
    }
    description
      "Grouping for y.1731";
  }

  // NSO-REMOVED START
  // grouping site-service-qos-profile {
  // container qos {
  //   if-feature "vpn-common:qos";
  //   container qos-classification-policy {
  //     list rule {
  //       key "id";
  //       ordered-by user;
  //       leaf id {
  //         type string;
  //         description
  //           "A description identifying the
  //            qos-classification-policy rule.";
  //       }
  //       choice match-type {
  //         default "match-flow";
  //         case match-flow {
  //           choice l3 {
  //             container ipv4 {
  //               uses packet-fields:acl-ip-header-fields;
  //               uses packet-fields:acl-ipv4-header-fields;
  //               description
  //                 "Rule set that matches IPv4 header.";
  //             }
  //             container ipv6 {
  //               uses packet-fields:acl-ip-header-fields;
  //               uses packet-fields:acl-ipv6-header-fields;
  //               description
  //                 "Rule set that matches IPv6 header.";
  //             }
  //             description
  //               "Either IPv4 or IPv6.";
  //           }
  //           choice l4 {
  //             container tcp {
  //               uses packet-fields:acl-tcp-header-fields;
  //               uses ports;
  //               description
  //                 "Rule set that matches TCP header.";
  //             }
  //             container udp {
  //               uses packet-fields:acl-udp-header-fields;
  //               uses ports;
  //               description
  //                 "Rule set that matches UDP header.";
  //             }
  //             description
  //               "Can be TCP or UDP";
  //           }
  //         }
  //         case match-application {
  //           leaf match-application {
  //             type identityref {
  //               base vpn-common:customer-application;
  //             }
  //             description
  //               "Defines the application to match.";
  //           }
  //         }
  //         description
  //           "Choice for classification.";
  //       }
  //       leaf target-class-id {
  //         type string;
  //         description
  //           "Identification of the class of service.
  //            This identifier is internal to the administration.";
  //       }
  //       description
  //         "List of marking rules.";
  //     }
  //     description
  //       "Configuration of the traffic classification policy.";
  //   }
  //   container qos-profile {
  //     list qos-profile {
  //       key profile;
  //       description
  //         "QoS profile.
  //          Can be standard profile or customized profile.";
  //         leaf profile {
  //           type leafref {
  //             path "/l2vpn-ntw/vpn-profiles/"
  //                + "valid-provider-identifiers"
  //                + "/qos-profile-identifier/id";
  //           }
  //           description
  //             "QoS profile to be used.";
  //         }
  //         leaf direction {
  //           type identityref {
  //             base vpn-common:qos-profile-direction;
  //           }
  //           default "vpn-common:both";
  //           description
  //             "The direction to which the QoS profile
  //              is applied.";
  //         }
  //     }
  //     description
  //       "QoS profile configuration.";
  //   }
  //   description
  //     "QoS configuration.";
  // }
  //   description
  //     "This grouping defines QoS parameters
  //      for a site";
  // }
  // NSO-REMOVED END

  // NSO ADDITION START
  grouping subinterface-rewrite-common-grouping {
    container ingress {
      tailf:info "Set the tag rewriting policy for this EFP";
      description "Set the tag rewriting policy for this EFP";
      presence "true";
      choice tag-choice {
        leaf pop {
          tailf:info "Remove one or more tags";
          description "Remove one or more tags";
          when "../../../../../encapsulation-type = 'vpn-common:dot1q'";
          type enumeration {
            enum "1" {
              tailf:info "Remove outer tag only";
            }
            enum "2" {
              tailf:info "Remove two outermost tags";
            }
          }
          mandatory true;
        }
        leaf push {
          tailf:info "Push one or more tags";
          description "Push one or more tags";
          type empty;
          mandatory true;
        }
        leaf translate {
          tailf:info "Replace tags with other tags";
          description "Replace tags with other tags";
          type enumeration {
            enum "1-to-1" {
              tailf:info "Replace the outermost tag with another tag";
            }
          }
          mandatory true;
        }
      }

      must "pop!='' or push or translate!=''" {
        error-message "Please provide at least one of the tag-choices: pop, push or translate.";
      }

      leaf dot1q {
        tailf:info "<1-4094> - Push a Dot1Q tag";
        description "<1-4094> - Push a Dot1Q tag";
        when "not(../pop)";
        mandatory true;
        type uint16 {
          tailf:info "<1-4094>;;VLAN Id to push";
          range "1..4094";
        }
      }

      leaf mode {
        type enumeration {
          enum symmetric {
            tailf:info "All rewrites must be symmetric";
          }
        }
      }
    }
  }
  // NSO ADDITION END

  /* MAIN L2VPN SERVICE */
  container l2vpn-ntw {
    /// NSO-REMOVED START
    // container vpn-profiles {
    // uses vpn-common:vpn-profile-cfg;
    //   description
    //     "Container for VPN Profiles.";
    // }
    /// NSO-REMOVED END

    // NSO ADDITION START
    container id-pools {
      presence "true";
      leaf evi-id-pool-name {
        type leafref {
          path "/ralloc:resource-pools/idalloc:id-pool/idalloc:name";
        }
        tailf:info "Select a Resource pool from which EVI-ID will be auto assigned ";
        description "Select a Resource pool from which EVI-ID will be auto assigned ";
      }
      leaf evi-source-target-pool-name {
        type leafref {
          path "/ralloc:resource-pools/idalloc:id-pool/idalloc:name";
        }
        tailf:info "Select a resource pool that will be used to auto-assign EVI source target identifier.";
        description "Select a resource pool that will be used to auto-assign EVI source target identifier.";
      }
      tailf:info "id-pools are used for evi-id, evi-source and evi-target configs.";
      description "id-pools are used for evi-id, evi-source and evi-target configs.";
    }
    // NSO ADDITION END

    container vpn-services {
      list vpn-service {
        key "vpn-id";
        leaf vpn-id {
          type vpn-common:svc-id;
          description
            "Refers to unique identifier for the L2NM.";
          tailf:info "Refers to unique identifier for the L2NM";
        }
        // NSO ADDITION START
        container evi-allocation-data {
          config false;
          tailf:cdb-oper {
            tailf:persistent true;
          }
          leaf evi-id {
              tailf:info "evi-id allocated by resource-manager id-allocator";
              description "evi-id allocated by resource-manager id-allocator";
              type string;
          }
          leaf evi-source {
              tailf:info "evi-source allocated by resource-manager id-allocator";
              description "evi-source allocated by resource-manager id-allocator";
              type string;
          }
          leaf evi-target {
              tailf:info "evi-target allocated by resource-manager id-allocator";
              description "evi-target allocated by resource-manager id-allocator";
              type string;
          }
          tailf:info "EVI resource allocations";
          description "EVI resource allocations";
        }

        uses ncs:service-data;
        ncs:servicepoint ietf-l2vpn-ntw-servicepoint;

        tailf:validate "ietf-l2vpn-nm-validation" {
            tailf:dependency ".";
        }

        uses ct-hook:template-hook;

        choice evi-id-choice {
          when "vpn-svc-type = 'vpn-common:evpn-bgp'";
          default "auto-evi-id";
          leaf auto-evi-id {
            type empty;
            tailf:info "Auto allocate Local EVI Id";
            description "Auto allocate Local EVI Id";
          }
          leaf evi-id {
            tailf:info "<1-65534> - EVI Id";
            description "<1-65534> - EVI Id";
            type uint16 {
              tailf:info "<1-65534>;;Ethernet VPN ID to set";
              range "1..65534";
            }
            mandatory true;
          }
        }
        choice evi-source-choice {
          when "vpn-svc-type = 'vpn-common:evpn-bgp' and not(vpn-nodes/vpn-node[1]/signaling-options/evpn-bgp/type = 'evpn-pbb')";
          default "auto-evi-source";
          leaf auto-evi-source {
            type empty;
            tailf:info "Auto allocate Local ACI Id";
            description "Auto allocate Local ACI Id";
          }
          leaf evi-source {
            tailf:info "<1-16777215> - Local ACI Id";
            description "<1-16777215> - Local ACI Id";
            type uint32 {
              tailf:info "<1-16777215>;;Source ac-id (hex or decimal format)";
              range "1..16777215";
            }
            mandatory true;
          }
        }
        choice evi-target-choice {
          when "vpn-svc-type = 'vpn-common:evpn-bgp' and not(vpn-nodes/vpn-node[1]/signaling-options/evpn-bgp/type = 'evpn-pbb')";
          default "auto-evi-target";
          leaf auto-evi-target {
            type empty;
            tailf:info "Auto allocate Remote ACI Id";
            description "Auto allocate Remote ACI Id";
          }
          leaf evi-target {
            tailf:info "<1-16777215> - Remote ACI Id";
            description "<1-16777215> - Remote ACI Id";
            type uint32 {
              tailf:info "<1-16777215>;;Remote ac-id (hex or decimal format)";
              range "1..16777215";
            }
            mandatory true;
          }
        }

        tailf:action self-test {
          tailf:actionpoint ietf-l2vpn-nm-self-test-actionpoint;
          input {
          }
          output {
            leaf status {
              type string;
            }
            leaf message {
              type string;
            }
          }
        }

        leaf control-word {
          when "../vpn-svc-type = 'vpn-common:t-ldp'";
          tailf:info "Control Word";
          description "Control Word";
          type enumeration {
            enum yes;
            enum no;
          }
          default no;
        }
        // NSO ADDITION END

        // NSO-REMOVED START
        // leaf l2sm-vpn-id {
        //   type vpn-common:svc-id;
        //   description
        //     "Pointer to the L2SM service.";
        // }
        // NSO-REMOVED END
        leaf vpn-svc-type {
          type identityref {
            base vpn-common:vpn-signaling-type;
          }
          description
            "Service type.";
          tailf:info
            "Service type.";
        }
        // NSO-REMOVED START
        // leaf customer-name {
        //   type string;
        //   description
        //     "Customer name";
        // }
        // NSO-REMOVED END

        leaf svc-topo {
          // NSO ADDITION START
          when "../vpn-svc-type = 'vpn-common:evpn-bgp'";
          // NSO ADDITION END
          type identityref {
            base vpn-common:vpn-topology;
          }
          description
            "Defining service topology, such as
             any-to-any,hub-spoke, etc.";
          tailf:info
            "Defining service topology, such as
             any-to-any,hub-spoke, etc.";
        }

        // NSO ADDITION START
        container vpn-target {
          presence true;
          when "../svc-topo = 'vpn-common:any-to-any' or ../svc-topo = 'vpn-common:hub-spoke'";
          tailf:info "VPN Target";
          description "VPN Target";

          leaf hub-rt-value {
            tailf:info "Hub Route-Target Value";
            description "Hub Route-Target Value";
            type rt-types:route-target;
            mandatory true;
          }

          leaf spoke-rt-value {
            when "../../svc-topo = 'vpn-common:hub-spoke'";
            tailf:info "Spoke Route-Target Value";
            description "Spoke Route-Target Value";
            type rt-types:route-target;
            mandatory true;
          }
        }
        // NSO ADDITION END

        uses vpn-common:service-status;

        // container multicast-like {
        //   if-feature "vpn-common:multicast";
        //   leaf enabled {
        //     type boolean;
        //     default "false";
        //     description
        //       "Enables multicast.";
        //   }
        //   container customer-tree-flavors {
        //     leaf-list tree-flavor {
        //       type identityref {
        //         base vpn-common:multicast-tree-type;
        //       }
        //       description
        //         "Type of tree to be used.";
        //     }
        //     description
        //       "Type of trees used by customer.";
        //   }
        //   description
        //   "Multicast like container";
        // }

        // container extranet-vpns {
        //   if-feature "vpn-common:extranet-vpn";
        //   list extranet-vpn {
        //     key "vpn-id";
        //     leaf vpn-id {
        //       type vpn-common:svc-id;
        //       description
        //         "Identifies the target VPN.";
        //     }
        //     leaf local-sites-role {
        //       type identityref {
        //         base vpn-common:site-role;
        //       }
        //       default "vpn-common:any-to-any-role";
        //       description
        //         "This describes the role of the
        //           local sites in the target VPN topology.";
        //     }
        //     description
        //       "List of extranet VPNs the local VPN is attached to.";
        //   }
        //   description
        //     "Container for extranet VPN configuration.";
        // }

        // leaf svc-mtu {
        //   type uint32;
        //   description
        //     "SVC MTU, it is also known as the maximum transmission unit
        //       or maximum frame size,When a frame is larger than the MTU,
        //       it is broken down, or fragmented, into smaller pieces by the
        //       network protocol to accommodate the MTU of the network";
        // }

        // leaf ce-vlan-preservation {
        //   type boolean;
        //   description
        //     "Preserve the CE-VLAN ID from ingress to egress,i.e.,
        //       CE-VLAN tag of the egress frame are identical to
        //       those of the ingress frame that yielded this egress
        //       service frame. If All-to-One bundling within a site
        //       is Enabled, then preservation applies to all Ingress
        //       service frames. If All-to-One bundling is Disabled,
        //       then preservation applies to tagged Ingress service
        //       frames having CE-VLAN ID 1 through 4094.";
        // }

        // leaf ce-vlan-cos-perservation {
        //   type boolean;
        //   description
        //     "CE vlan CoS preservation. PCP bits in the CE-VLAN tag
        //       of the egress frame are identical to those of the ingress
        //       frame that yielded this egress service frame.";
        // }

        // uses vpn-common:svc-transport-encapsulation;
        // NSO-REMOVED END
        container vpn-nodes {
          when "../vpn-svc-type != ''";
          list vpn-node {
            key "vpn-node-id ne-id";
            leaf vpn-node-id {
              type vpn-common:svc-id;
              description "Local or Remote Device";
              tailf:info "Local or Remote Device";
            }

            // NSO ADDITION START
            uses ct-hook:template-hook;
            tailf:action error-recovery {
              tailf:actionpoint ietf-l2vpn-nm-vpn-node-error-recovery;
              tailf:info "Action to recover this device during create/update from a transient failures
                          like device connection issues once the device is reachable again.
                          For create/update failures, this action issues a sync on the device
                          & redeploys the service with reconcile option.";
              description "Action to recover this device during create/update from a transient
                          failures like device connection issues once the device is reachable again.
                          For create/update failures, this action issues a sync on the device
                          & redeploys the service with reconcile option.";
              input {
                leaf sync-direction {
                  tailf:info "sync device with sync-from or sync-to";
                  description "sync device with sync-from or sync-to";
                  type enumeration {
                    enum sync-from;
                    enum sync-to;
                  }
                  mandatory true;
                }
              }
              output {
                leaf success {
                  type boolean;
                  mandatory true;
                }
                leaf detail {
                  type string;
                }
              }
              tailf:confirm-text "########################\n" +
                "#        Warning       #\n" +
                "########################\n" +
                "You are about to recover a T-SDN service.\n" +
                "This will issue a sync on the device.\n" +
                "Are you sure you want to proceed?" {
                  tailf:confirm-default false;
              }
            }

            container multi-home {
              when "../../../vpn-svc-type = 'vpn-common:evpn-bgp'";
              presence "true";
              leaf esi-value {
                tailf:info "<0-ff> 9-octet ESI value. 00.00.00.00.00.00.00.00.00 is not allowed";
                description "<0-ff> 9-octet ESI value. 00.00.00.00.00.00.00.00.00 is not allowed";
                type string {
                  tailf:info "<0-ff> 9-octet ESI value. 00.00.00.00.00.00.00.00.00 is not allowed";
                  pattern '[0-9a-f]{2}(\.[0-9a-f]{2}){8}';
                  pattern '00\.00\.00\.00\.00\.00\.00\.00\.00' {
                    modifier invert-match;
                  }
                }
                mandatory true;
              }
            }

            container te-service-mapping {
              container te-mapping {
                choice te {
                  container sr-policy {
                    // NSO ADDITION START
                    when "not(../../../signaling-options/evpn-bgp/type = 'evpn-pbb')";
                    // NSO ADDITION END
                    presence true;
                    // TODO: Circuit Style, ETA: TSDN 5.0
                    // leaf policy-type {
                    //   type enumeration {
                    //     enum policy;
                    //     enum cs-policy;
                    //   }
                    //   default policy;
                    // }

                    leaf policy {
                      tailf:info "Name of SR TE policy";
                      description "Name of SR TE policy";
                      type string;
                      mandatory true;
                    }
                    leaf fallback {
                      tailf:info "Fallback option for preferred path";
                      description "Fallback option for preferred path";
                      type enumeration {
                        enum disable {
                          tailf:info "Disable fallback for preferred path";
                        }
                      }
                    }
                    tailf:info "SR Policy for TE mapping.
                    			L2VPN association with SRv6-TE (SR Policy and ODN) is not supported for this release";
                    description "SR Policy for TE mapping.
                    			L2VPN association with SRv6-TE (SR Policy and ODN) is not supported for this release";
                  }//case sr-policy

                  container te-tunnel-list {
                    when "../../../../../vpn-svc-type != 'vpn-common:evpn-bgp'";
                    presence true;
                    choice tunnel-te-id-source {
                      mandatory true;
                      leaf te-tunnel-id {
                        tailf:info "Specify tunnel number for preferred path <0-65535>";
                        description "Specify tunnel number for preferred path <0-65535>";
                        type uint16;
                      }
                      leaf ietf-te-service {
                        tailf:info "Specify IETF-TE service name from which tunnel-te id will be extracted";
                        description "Specify IETF-TE service name from which tunnel-te id will be extracted";
                        type string;
                      }
                    }
                    leaf fallback {
                      tailf:info "Fallback option for preferred path";
                      description "Fallback option for preferred path";
                      type enumeration {
                        enum disable {
                          tailf:info "Disable fallback for preferred path";
                        }
                      }
                    }
                  }//case te-tunnel-list

                  container odn {
                    when "../../../../../vpn-svc-type = 'vpn-common:evpn-bgp'";
                    presence true;
                    leaf route-policy {
                      tailf:info "Route policy definition";
                      description "Route policy definition";
                      type leafref {
                        path "/cisco-flat-L2vpn-fp:l2vpn-route-policy/cisco-flat-L2vpn-fp:name";
                      }
                      mandatory true;
                    }

                    container attach-point {
                      choice parent-rr-route-policy-choice {
                        leaf parent-rr-route-policy {
                          type string;
                          tailf:info "Parent RR Route Policy to apply local route policies";
                          description "Parent RR Route Policy to apply local route policies";
                        }
                      }
                      tailf:info "Name of attach point where policy is attached";
                      description "Name of attach point where policy is attached";
                    }
                    must "not(route-policy) or attach-point/parent-rr-route-policy or ../../../signaling-options/evpn-bgp/type = 'evpn-pbb'" {
                      error-message "If route-policy is defined, parent-rr-route-policy-choice " +
                                    "must be selected";
                    }
                    tailf:info "ODN SR Policy.
                    			L2VPN association with SRv6-TE (SR Policy and ODN) is not supported for this release";
                    description "ODN SR Policy.
                    			L2VPN association with SRv6-TE (SR Policy and ODN) is not supported for this release";
                  }//case odn
                }
                tailf:info "TE Service Mapping";
                description "TE Service Mapping";
              }
              tailf:info "Mapping of this service to an optional Traffic Engineered path";
              description "Mapping of this service to an optional Traffic Engineered path";
            }
            // NSO ADDITION END

            // NSO-REMOVED START
            // leaf description {
            //   type string;
            //   description
            //     "Textual description of a VPN node.";
            // }
            // NSO-REMOVED END

            leaf node-role {
              // NSO ADDITION START
              when "../../../l2vpn-ntw:svc-topo != 'vpn-common:any-to-any'";
              // NSO ADDITION END
              type identityref {
                base vpn-common:site-role;
              }
              default "vpn-common:any-to-any-role";
              description
                "Role of the vpn-node in the IP VPN.";
              tailf:info
                "Role of the vpn-node in the IP VPN.";
            }

            leaf ne-id {
              type string;
              description
                "Local or Remote Device.";
              tailf:info
                "Local or Remote Device.";
            }

            // NSO ADDITION START
            must 'ne-id = vpn-node-id'{
              error-message "vpn-node-id and ne-id must be same";
            }
            // NSO ADDITION END

            // NSO-REMOVED START
            // leaf port-id {

            //   type string;
            //   description
            //     "NE Port-id";
            //   tailf:info "Interfacce Port";
            // }

            // uses vpn-common:service-status;
            // NSO-REMOVED END

            list signaling-options {
              key "type";
              leaf type {
                type identityref {
                  base vpn-common:vpn-signaling-type;
                }
                description
                  "VPN signaling types. Only one signaling option can be given per VPN node";
                tailf:info
                  "VPN signaling types. Only one signaling option can be given per VPN node";
              }

              // NSO ADDITION START
              must 'type = ../../../vpn-svc-type'{
                error-message "signaling-options type and vpn-svc-type must be same";
              }
              // NSO ADDITION END

              // NSO-REMOVED START
              // container l2vpn-bgp {
              //   when "../type = 'vpn-common:l2vpn-bgp'" {
              //     description
              //       "Only applies when vpn signaling type is l2vpn
              //        BGP protocol.";
              //   }
              //   leaf pwe-encapsulation-type {
              //     type identityref {
              //       base vpn-common:encapsulation-type;
              //     }
              //     description
              //       "PWE Encapsulation Type";
              //   }
              //   uses vpn-common:vpn-route-targets;
              //   container pwe-mtu {
              //     leaf allow-mtu-mismatch {
              //       type boolean;
              //       description
              //         "Allow MTU mismatch";
              //     }
              //     description
              //       "Container of PWE MTU configurations";
              //   }
              //   leaf address-family {
              //   type vpn-common:address-family;
              //   description
              //     "Address family used for router-id information.";
              //   }
              //   description
              //     "Container for MP BGP L2VPN";
              // }
              // NSO-REMOVED END

              container evpn-bgp {
                presence "true";
                when "../type = 'vpn-common:evpn-bgp'" {
                  description
                    "Only applies when vpn signaling type is EVPN
                      BGP protocol.";
                }

                // NSO-REMOVED START
                // leaf vpn-id {
                //   type leafref {
                //     path "/l2vpn-ntw/vpn-services/vpn-service/vpn-id";
                //   }
                //   description
                //     "Identifies the target EVPN";
                //   tailf:info "Identifies the target EVPN";
                // }
                // NSO-REMOVED END

                leaf type {
                  type identityref {
                    base evpn-type;
                  }
                  description
                    "L2VPN types.";
                  tailf:info
                    "L2VPN types.";
                }

                // NSO-REMOVED START
                // leaf address-family {

                // type vpn-common:address-family;
                // description
                //   "Address family used for router-id information.";
                // tailf:info "Address family used for router-id information.";
                // }

                leaf mac-learning-mode {
                  // NSO ADDITION START
                  when "../type = 'evpn-pbb'";
                  // NSO ADDITION END
                  type identityref {
                    base mac-learning-mode;
                  }
                  description
                    "Indicates through which plane MAC addresses are
                      advertised.";
                  tailf:info
                    "Indicates through which plane MAC addresses are
                      advertised.";
                }

                // NSO ADDITION START
                uses vpn-common:vpn-route-targets {
                  when "type = 'evpn-pbb'";
                }
                // NSO ADDITION END

                // leaf arp-suppress {
                //   type boolean;
                //   default "false";
                //   description
                //     "Indicates whether to suppress ARP broadcast.";
                // }
                // NSO-REMOVED END

                description
                  "Container for MP BGP L2VPN";
                tailf:info "Container for MP BGP L2VPN";
              }
              container t-ldp-pwe {
                presence "true";
                when "../type = 'vpn-common:t-ldp'" {
                  description
                    "Only applies when vpn signaling type is Target LDP.";
                }
                // NSO-REMOVED START
                // leaf type {
                //   type identityref {
                //     base t-ldp-pwe-type;
                //   }
                //   description
                //     "T-LDP PWE type";
                //   tailf:info "T-LDP PWE type";
                // }

                // leaf pwe-encapsulation-type {
                //   type identityref {
                //     base vpn-common:encapsulation-type;
                //   }
                //   description
                //     "PWE Encapsulation Type.";
                // }

                // leaf pwe-mtu {
                //   type uint16;
                //     description
                //       "Allow MTU mismatch";
                // }
                // NSO-REMOVED END

                list ac-pw-list {
                  key "peer-addr vc-id";
                  leaf peer-addr {
                    type inet:ip-address;
                    description
                      "Peer IP address. Only one peer IP can be given.";
                    tailf:info "Peer IP address. Only one peer IP can be given.";
                  }
                  leaf vc-id {
                    type vpn-common:svc-id;
                    description
                      "VC label used to identify PW.";
                    tailf:info "VC label used to identify PW.";
                  }
                  // NSO ADDITION START
                  leaf mpls-label {
                    tailf:info "<16-1048575> - MPLS Label.
                      Use a value within the global range defined for the chosen device.";
                    description "<16-1048575> - MPLS Label
                      Use a value within the global range defined for the chosen device.";
                    type uint32 {
                      range "16..1048575";
                    }
                  }
                  // NSO ADDITION END
                  // NSO-REMOVED START
                  // leaf pw-type {
                  //   type identityref {
                  //     base vpn-common:vpn-topology;
                  //   }
                  //   description
                  //     "PW topology type";
                  // }

                  // leaf pw-priority {
                  //   type uint32;
                  //   description
                  //     "Defines the priority for the PW.
                  //      The higher the pw-priority value,
                  //      the higher the preference of the PW will be.";
                  // }
                  // NSO-REMOVED END
                  description
                    "List of AC and PW bindings.";
                  tailf:info "List of AC and PW bindings.";
                }
                // NSO-REMOVED START
                // container qinq {
                //   when "/l2vpn-ntw/vpn-services/vpn-service/vpn-nodes/vpn-node/signaling-options/type = 'vpn-common:h-vpls'" {
                //     description
                //       "Only applies when t-ldp pwe type is h-vpls.";
                //   }
                //   leaf s-tag {
                //     type uint32;
                //     description
                //       "S-TAG";
                //   }
                //   leaf c-tag {
                //     type uint32;
                //     description
                //       "C-TAG";
                //   }
                //   description
                //     "Container for QinQ";
                // }
                // NSO-REMOVED END
                description
                  "Container of T-LDP PWE configurations";
                tailf:info "Container of T-LDP PWE configurations";
              }
              // NSO-REMOVED START
              // container l2tp-pwe {
              //   when "../type = 'vpn-common:l2tp'" {
              //     description
              //       "Applies when vpn signaling type is L2TP protocol.";
              //   }
              //   leaf type {
              //     type identityref {
              //       base t-ldp-pwe-type;
              //     }
              //     description
              //       "T-LDP PWE type";
              //   }
              //   leaf encapsulation-type {
              //     type identityref {
              //       base vpn-common:encapsulation-type;
              //     }
              //     description
              //       "Encapsulation type";
              //   }
              //   list ac-pw-list {
              //     key "peer-addr vc-id";
              //     leaf peer-addr {
              //       type inet:ip-address;
              //       description
              //         "Peer IP address.";
              //     }
              //     leaf vc-id {
              //       type string;
              //       description
              //         "VC lable used to identify PW.";
              //     }
              //     leaf pw-priority {
              //       type uint32;
              //       description
              //         "PW priority";
              //     }
              //     description
              //       "List of AC and PW bindings.";
              //     tailf:info
              //       "AC and PW bindings.";
              //   }
              //   description
              //     "Container for l2tp pw";
              // }
              // NSO-REMOVED END
              description
                "List of VPN Signaling Option.";
              tailf:info
                "VPN Signaling Option.";
            }

            container vpn-network-accesses {
              list vpn-network-access {
                key "id";
                leaf id {
                  type vpn-common:svc-id;
                  description
                    "Identifier of network access. Only one VPN id can be given for a VPN node.";
                  tailf:info "Identifier of network access. Only one VPN id can be given for a VPN node.";
                }

                // NSO-REMOVED START
                // leaf description {
                //   type string;
                //   description
                //     "String to describe the element.";
                // }
                // NSO-REMOVED END

                leaf Interface-mtu {
                  type uint32;
                  description
                    "<64-65535>;;Interface MTU, it is also known as the maximum
                     transmission unit or maximum frame size. When a
                     frame is larger than the MTU, it is broken down,
                     or fragmented, into smaller pieces by the
                     network protocol to accommodate the MTU of the network.
                	 Please check the supported range defined for the chosen device.";
                  tailf:info
                    "<64-65535>;;Interface MTU, it is also known as the maximum
                     transmission unit or maximum frame size. When a
                     frame is larger than the MTU, it is broken down,
                     or fragmented, into smaller pieces by the
                     network protocol to accommodate the MTU of the network.
                     Please check the supported range defined for the chosen device.";
                }
                // NSO-REMOVED START
                // uses vpn-common:service-status;

                // container access-diversity {
                //   if-feature "vpn-common:site-diversity";
                //       container groups {
                //         leaf fate-sharing-group-size {
                //           type uint16;
                //           description
                //             "Fate sharing group size.";
                //         }
                //         leaf group-color {
                //           type string;
                //           description
                //             "Group color associated with a particular VPN.";
                //         }
                //         list group {
                //           key "group-id";
                //           leaf group-id {
                //             type string;
                //             description
                //               "Group-id the site network access
                //                is belonging to";
                //           }
                //           description
                //             "List of group-id";
                //         }
                //         description
                //           "Groups the fate sharing group member
                //            is belonging to";
                //       }

                //   container constraints {
                //     list constraint {
                //       key "constraint-type";
                //       leaf constraint-type {
                //         type identityref {
                //           base placement-diversity;
                //         }
                //         description
                //           "Diversity constraint type.";
                //       }
                //       container target {
                //         choice target-flavor {
                //           case id {
                //             list group {
                //               key "group-id";
                //               leaf group-id {
                //                 type string;
                //                 description
                //                   "The constraint will apply
                //                    against this particular
                //                    group-id";
                //               }
                //               description
                //                 "List of groups";
                //             }
                //           }
                //           case all-accesses {
                //             leaf all-other-accesses {
                //               type empty;
                //               description
                //                 "The constraint will apply
                //                  against all other site network
                //                  access of this site";
                //             }
                //           }
                //           case all-groups {
                //             leaf all-other-groups {
                //               type empty;
                //               description
                //                 "The constraint will apply
                //                  against all other groups the
                //                  customer is managing";
                //             }
                //           }
                //           description
                //             "Choice for the group definition";
                //         }
                //         description
                //           "The constraint will apply against
                //            this list of groups";
                //       }
                //       description
                //         "List of constraints";
                //     }
                //     description
                //       "Constraints for placing this site
                //         network access";
                //   }
                //   description
                //     "Diversity parameters.";
                // }
                // NSO-REMOVED END

                container connection {

                  leaf encapsulation-type {
                    type identityref {
                      base vpn-common:encapsulation-type;
                    }
                    description
                      "Encapsulation Type.";
                    tailf:info
                      "Encapsulation Type.";
                  }

                  // NSO-REMOVED START
                  // leaf-list eth-inf-type {
                  //   type identityref {
                  //     base vpn-common:encapsulation-type;
                  //   }
                  //   description
                  //     "Ethernet Interface Type";
                  // }
                  // NSO-REMOVED END

                  container dot1q-interface {
                    presence "true";
                    when "../encapsulation-type != 'vpn-common:untagged-int'";
                    leaf l2-access-type {
                      type identityref {
                        base vpn-common:encapsulation-type;
                      }
                      description
                        "L2 Access Encapsulation Type.";
                      tailf:info
                        "L2 Access Encapsulation Type.";
                    }
                    container dot1q {
                      presence "true";
                      when "../l2-access-type='vpn-common:dot1q'";
                      if-feature "dot1q";
                      leaf physical-inf {
                        type string;
                        description
                          "Physical Interface";
                        tailf:info "Physical Interface";
                      }
                      leaf c-vlan-id {
                        type uint32;
                        description
                          "VLAN identifier";
                        tailf:info "VLAN identifier";
                      }

                      // NSO ADDITION START
                      container rewrite {
                        tailf:info "Tag Rewrite";
                        description "Tag Rewrite";
                        presence "true";
                        when "../c-vlan-id";
                        uses subinterface-rewrite-common-grouping;
                      }
                      // NSO ADDITION END

                      description
                        "dot1q";
                      tailf:info "dot1q";
                    }

                    // NSO-REMOVED START
                    // container qinq {
                    //   when "../l2-access-type='vpn-common:qinq'";
                    //   if-feature "qinq";
                    //   leaf s-vlan-id {
                    //     type uint32;
                    //     description
                    //       "S-VLAN Identifier";
                    //   }
                    //   leaf c-vlan-id {
                    //     type uint32;
                    //     description
                    //       "C-VLAN Identifier";
                    //   }
                    //   description
                    //     "QinQ";
                    // }

                    // container qinany {
                    //   if-feature "vpn-common:qinany";
                    //   leaf s-vlan-id {
                    //     type uint32;
                    //     description
                    //       "S-Vlan ID";
                    //   }
                    //   description
                    //     "Container for Q in Any";
                    // }

                    // container vxlan {
                    //   when "../l2-access-type='vpn-common:vxlan'";
                    //   if-feature "vxlan";
                    //   leaf vni-id {
                    //     type uint32;
                    //     description
                    //       "VNI Identifier";
                    //   }
                    //   leaf peer-mode {
                    //     type identityref {
                    //       base vpn-common:vxlan-peer-mode;
                    //     }
                    //     description
                    //       "specify the vxlan access mode";
                    //   }
                    //   list peer-list {
                    //     key "peer-ip";
                    //     leaf peer-ip {
                    //       type inet:ip-address;
                    //       description
                    //         "Peer IP";
                    //     }
                    //     description
                    //       "List for peer IP";
                    //   }
                    //   description
                    //     "QinQ";
                    // }
                    /// NSO-REMOVED END
                    description
                      "Container for dot1Q Interface";
                    tailf:info "Container for dot1Q Interface";
                  }

                  // NSO ADDITION START
                  container untagged-interface {
                    when "../encapsulation-type = 'vpn-common:untagged-int'";
                    presence "true";
                    leaf l2-access-type {
                      type identityref {
                        base vpn-common:encapsulation-type;
                      }
                      description
                        "L2 Access Encapsulation Type.";
                      tailf:info
                        "L2 Access Encapsulation Type.";
                    }
                    container untagged {
                      when "../l2-access-type='vpn-common:untagged-int'";
                      presence "true";
                      leaf physical-inf {
                        type string;
                        description
                          "Physical Interface";
                        tailf:info "Physical Interface";
                      }
                      leaf sub-if-id {
                        type uint32;
                        description
                          "Sub Interface Id";
                        tailf:info "Sub Interface Id";
                      }
                      container rewrite {
                        tailf:info "Tag Rewrite";
                        description "Tag Rewrite";
                        presence "true";
                        when "../sub-if-id";
                        uses subinterface-rewrite-common-grouping;
                      }
                      description
                        "Untagged";
                      tailf:info "Untagged";
                    }
                    description
                      "Container for untagged Interface";
                    tailf:info
                      "Container for untagged Interface";
                  }
                  // NSO ADDITION END

                  // NSO-REMOVED START
                  // container phy-interface {
                  //   leaf port-number {
                  //     type uint32;
                  //     description
                  //       "Port number";
                  //   }
                  //   leaf port-speed {
                  //     type uint32;
                  //     description
                  //       "Port speed";
                  //   }
                  //   leaf mode {
                  //     type neg-mode;
                  //     description
                  //       "Negotiation mode";
                  //   }
                  //   leaf phy-mtu {
                  //     type uint32;
                  //     description
                  //       "PHY MTU";
                  //   }
                  //   leaf flow-control {
                  //     type string;
                  //     description
                  //       "Flow control";
                  //   }
                  //   container oam-802.3ah-link {
                  //     if-feature "oam-3ah";
                  //     leaf enable {
                  //       type boolean;
                  //       description
                  //         "Indicate whether support oam 802.3 ah link";
                  //     }
                  //     description
                  //       "Container for oam 802.3 ah link.";
                  //   }
                  //   leaf uni-loop-prevention {
                  //     type boolean;
                  //     description
                  //       "If this leaf set to truth that the port automatically
                  //         goes down when a physical loopback is detect.";
                  //   }
                  //   description
                  //     "Container of PHY Interface Attributes configurations";
                  // }
                  // container lag-interface {
                  //   if-feature "vpn-common:lag-interface";
                  //   list lag-interface {
                  //     key "lag-interface-number";
                  //     leaf lag-interface-number {
                  //       type uint32;
                  //       description
                  //         "LAG interface number";
                  //     }
                  //     container lacp {
                  //       leaf lacp-state {
                  //         type boolean;
                  //         description
                  //           "LACP on/off";
                  //       }
                  //       leaf lacp-mode {
                  //         type boolean;
                  //         description
                  //           "LACP mode";
                  //       }
                  //       leaf lacp-speed {
                  //         type boolean;
                  //         description
                  //           "LACP speed";
                  //       }
                  //       leaf mini-link {
                  //         type uint32;
                  //         description
                  //           "The minimum aggregate bandwidth for a LAG";
                  //       }
                  //       leaf system-priority {
                  //         type uint16;
                  //         description
                  //           "Indicates the LACP priority for the system.
                  //             The range is from 0 to 65535.
                  //             The default is 32768.";
                  //       }

                  //       container member-link-list {
                  //         list member-link {
                  //           key "name";
                  //           leaf name {
                  //             type string;
                  //             description
                  //               "Member link name";
                  //           }
                  //           leaf port-speed {
                  //             type uint32;
                  //             description
                  //               "Port speed";
                  //           }
                  //           leaf mode {
                  //             type neg-mode;
                  //             description
                  //               "Negotiation mode";
                  //           }
                  //           leaf link-mtu {
                  //             type uint32;
                  //             description
                  //               "Link MTU size.";
                  //           }
                  //           container oam-802.3ah-link {
                  //             if-feature "oam-3ah";
                  //             leaf enable {
                  //               type boolean;
                  //               description
                  //                 "Indicate whether support oam 802.3 ah link";
                  //             }
                  //             description
                  //               "Container for oam 802.3 ah link.";
                  //           }
                  //           description
                  //             "Member link";
                  //         }
                  //         description
                  //           "Container of Member link list";
                  //       }
                  //       leaf flow-control {
                  //         type string;
                  //         description
                  //           "Flow control";
                  //       }
                  //       leaf lldp {
                  //         type boolean;
                  //         description
                  //           "LLDP";
                  //       }
                  //       description
                  //         "LACP";
                  //     }
                  //     description
                  //       "List of LAG interfaces";
                  //   }
                  //   description
                  //     "Container of LAG interface attributes configuration";
                  // }

                  // list cvlan-id-to-svc-map {
                  //   key "svc-id";
                  //   leaf svc-id {
                  //     type leafref {
                  //       path "/l2vpn-ntw/vpn-services/vpn-service/vpn-id";
                  //     }
                  //     description
                  //       "VPN Service identifier";
                  //   }
                  //   list cvlan-id {
                  //     key "vid";
                  //     leaf vid {
                  //       type uint32;
                  //       description
                  //         "CVLAN ID";
                  //     }
                  //     description
                  //       "List of CVLAN-ID to SVC Map configurations";
                  //   }
                  //   description
                  //     "List for cvlan-id to L2VPn Service map configurations";
                  // }

                  // NSO-REMOVED END
                  container split-horizon {
                    // NSO ADDITION START
                    when "../../../../node-role";
                    // NSO ADDITION END
                    // leaf group-name {
                    //   type string;
                    //   description
                    //     "group-name of the Split Horizon";
                    //   tailf:info
                    //     "group-name of the Split Horizon";
                    // }
                    description
                      "Configuration with split horizon enabled";
                    tailf:info
                      "Configuration with split horizon enabled";
                    leaf enable {
                      tailf:info "Enable split horizon";
                      description "Enable split horizon";
                      type boolean;
                      default "true";
                    }
                  }
                  description
                    "Container for bearer";
                  tailf:info "Container for bearer";
                }


                // NSO-REMOVED START
                // container availability {
                //   leaf access-priority {
                //     type uint32;
                //     description
                //       "Access priority";
                //   }
                //   choice redundancy-mode {
                //     case single-active {
                //       leaf single-active {
                //         type boolean;
                //         description
                //           "Single active";
                //       }
                //       description
                //         "Single active case";
                //     }
                //     case all-active {
                //       leaf all-active {
                //         type boolean;
                //         description
                //           "All active";
                //       }
                //       description
                //         "All active case";
                //     }
                //     description
                //       "Redundancy mode choice";
                //   }
                //   description
                //     "Container of availability optional configurations";
                // }

                // container service {
                //   container svc-input-bandwidth {
                //     if-feature "input-bw";
                //     list input-bandwidth {
                //       key "type";
                //       leaf type {
                //         type identityref {
                //           base vpn-common:bw-type;
                //         }
                //         description
                //           "Bandwidth Type";
                //       }
                //       leaf cos-id {
                //         type uint8;
                //         description
                //           "Identifier of Class of Service
                //             , indicated by DSCP or a CE-CLAN
                //             CoS(802.1p)value in the service frame.";
                //       }
                //       leaf cir {
                //         type uint64;
                //         description
                //           "Committed Information Rate. The maximum number of
                //             bits that a port can receive or send during
                //             one-second over an interface.";
                //       }
                //       leaf cbs {
                //         type uint64;
                //         description
                //           "Committed Burst Size.CBS controls the bursty nature
                //             of the traffic. Traffic that does not use the
                //             configured CIR accumulates credits until the credits
                //             reach the configured CBS.";
                //       }
                //       leaf eir {
                //         type uint64;
                //         description
                //           "Excess Information Rate,i.e.,Excess frame delivery
                //             allowed not subject to SLA.The traffic rate can be
                //             limited by eir.";
                //       }
                //       leaf ebs {
                //         type uint64;
                //         description
                //           "Excess Burst Size. The bandwidth available for burst
                //             traffic from the EBS is subject to the amount of
                //             bandwidth that is accumulated during periods when
                //             traffic allocated by the EIR policy is not used.";
                //       }
                //       leaf pir {
                //         type uint64;
                //         description
                //           "Peak Information Rate, i.e., maixmum frame delivery
                //             allowed. It is equal to or less than sum of cir and
                //             eir.";
                //       }
                //       leaf pbs {
                //         type uint64;
                //         description
                //           "Peak Burst Size. It is measured in bytes per second.";
                //       }
                //       description
                //         "List for input bandwidth";
                //     }
                //     description
                //       "From the PE perspective, the service input
                //         bandwidth of the connection.";
                //   }
                //   container svc-output-bandwidth {
                //     if-feature "output-bw";
                //     list output-bandwidth {
                //       key "type";
                //       leaf type {
                //         type identityref {
                //           base vpn-common:bw-type;
                //         }
                //         description
                //           "Bandwidth Type";
                //       }
                //       leaf cos-id {
                //         type uint8;
                //         description
                //           "Identifier of Class of Service
                //             , indicated by DSCP or a CE-CLAN
                //             CoS(802.1p)value in the service frame.";
                //       }
                //       leaf cir {
                //         type uint64;
                //         description
                //           "Committed Information Rate. The maximum number of
                //             bits that a port can receive or send during
                //             one-second over an interface.";
                //       }
                //       leaf cbs {
                //         type uint64;
                //         description
                //           "Committed Burst Size.CBS controls the bursty nature
                //             of the traffic. Traffic that does not use the
                //             configured CIR accumulates credits until the credits
                //             reach the configured CBS.";
                //       }
                //       leaf eir {
                //         type uint64;
                //         description
                //           "Excess Information Rate,i.e.,Excess frame delivery
                //             allowed not subject to SLA.The traffic rate can be
                //             limited by eir.";
                //       }
                //       leaf ebs {
                //         type uint64;
                //         description
                //           "Excess Burst Size. The bandwidth available for burst
                //             traffic from the EBS is subject to the amount of
                //             bandwidth that is accumulated during periods when
                //             traffic allocated by the EIR policy is not used.";
                //       }
                //       leaf pir {
                //         type uint64;
                //         description
                //           "Peak Information Rate, i.e., maixmum frame delivery
                //             allowed. It is equal to or less than sum of cir and
                //             eir.";
                //       }
                //       leaf pbs {
                //         type uint64;
                //         description
                //           "Peak Burst Size. It is measured in bytes per second.";
                //       }
                //       description
                //         "List for output bandwidth";
                //     }
                //     description
                //       "From the PE perspective, the service output
                //         bandwidth of the connection.";
                //   }

                //   uses site-service-qos-profile;

                //   container precedence {
                //     leaf precedence {
                //       type identityref {
                //         base precedence-type;
                //       }
                //       description
                //         "Defining service redundancy in transport
                //           network.";
                //     }
                //     description
                //       "Transport netowrk precedence selector
                //         Primary or Secondary tunnel.";
                //   }
                //   description
                //     "Container for service";
                // }

                // container broadcast-unknown-unicast-multicast {
                //   leaf multicast-site-type {
                //     type enumeration {
                //       enum receiver-only {
                //         description
                //           "The site only has receivers.";
                //       }
                //       enum source-only {
                //         description
                //           "The site only has sources.";
                //       }
                //       enum source-receiver {
                //         description
                //           "The site has both sources and receivers.";
                //       }
                //     }
                //     default "source-receiver";
                //     description
                //       "Type of multicast site.";
                //   }
                //   list multicast-gp-address-mapping {
                //     key "id";
                //     leaf id {
                //       type uint16;
                //       description
                //         "Unique identifier for the mapping.";
                //     }
                //     leaf vlan-id {
                //       type uint32;
                //       description
                //         "the VLAN ID of the Multicast group";
                //     }
                //     leaf mac-gp-address {
                //       type yang:mac-address;
                //       description
                //         "the MAC address of the Multicast group";
                //     }
                //     leaf port-lag-number {
                //       type uint32;
                //       description
                //         "the ports/LAGs belonging to the Multicast group";
                //     }
                //     description
                //       "List of Port to group mappings.";
                //   }
                //   leaf bum-overall-rate {
                //     type uint32;
                //     description
                //       "overall rate for BUM";
                //   }
                //   description
                //     "Container of broadcast, unknown unicast, and multicast
                //       configurations";
                // }
                // NSO-REMOVED END

                container ethernet-service-oam {
                  // NSO ADDITION START
                  when "not(../../../signaling-options/evpn-bgp/type = 'evpn-pbb')";
                  // NSO ADDITION END
                  leaf md-name {
                    type string;
                    description
                      "Maintenance domain name";
                    tailf:info "Maintenance domain name";
                  }
                  leaf md-level {
                    type uint8;
                    description
                      "Maintenance domain level";
                    tailf:info "Maintenance domain level";
                  }
                // NSO-REMOVED START
                //   container cfm-802.1-ag {
                //     list n2-uni-c {
                //       key "maid";
                //       uses cfm-802-grouping;
                //       description
                //         "List of UNI-N to UNI-C";
                //     }
                //     list n2-uni-n {
                //       key "maid";
                //       uses cfm-802-grouping;
                //       description
                //         "List of UNI-N to UNI-N";
                //     }
                //     description
                //       "Container of 802.1ag CFM configurations.";
                //   }
                // NSO-REMOVED END
                  uses y-1731;
                  description
                    "Container for Ethernet service OAM.";
                  tailf:info "Container for Ethernet service OAM.";
                }

                // container mac-loop-prevention {
                //   leaf frequency {
                //     type uint32;
                //     description
                //       "Frequency";
                //   }
                //   leaf protection-type {
                //     type identityref {
                //       base loop-prevention-type;
                //     }
                //     description
                //       "Protection type";
                //   }
                //   leaf number-retries {
                //     type uint32;
                //     description
                //       "Number of retries";
                //   }
                //   description
                //     "Container of MAC loop prevention.";
                // }

                // container access-control-list {
                //   list mac {
                //     key "mac-address";
                //     leaf mac-address {
                //       type yang:mac-address;
                //       description
                //         "MAC address.";
                //     }
                //     description
                //       "List for MAC.";
                //   }
                //   description
                //     "Container for access control List.";
                // }

                // container mac-addr-limit {
                //   leaf mac-num-limit {
                //     type uint16;
                //     description
                //       "maximum number of MAC addresses learned from
                //         the subscriber for a single service instance.";
                //   }
                //   leaf time-interval {
                //     type uint32;
                //     units "milliseconds";
                //     description
                //       "The aging time of the mac address.";
                //   }
                //   leaf action {
                //     type identityref {
                //       base mac-action;
                //     }
                //     description
                //       "specify the action when the upper limit is
                //         exceeded: drop the packet, flood the
                //         packet, or simply send a warning log message.";
                //   }
                //   description
                //     "Container of MAC-Addr limit configurations";
                // }
                // NSO-REMOVED END

                description
                  "VPN Network Accesses.";
                tailf:info
                  "VPN Network Accesses.";
              }
              description
                "List of VPN Nodes.";
              tailf:info "List of VPN Nodes";
            }
            description
              "Container of VPN Nodes.";
            tailf:info
              "Container of VPN Nodes.";
          }
          description
            "List of vpn-svc";
          tailf:info "List of vpn-svc";
        }
        description
          "Container of port configurations";
        tailf:info "Container of port configurations";
      }

      // NSO ADDITION START
      list vpn-service-plan {
        config false;
        tailf:cdb-oper {
          tailf:persistent true;
        }
        key "vpn-id";
        leaf vpn-id {
          type string;
        }

        uses ncs:nano-plan-data;
        uses ncs:nano-plan-history;
      }
      // NSO ADDITION END

      description
        "Container for L2VPN service";
      tailf:info "Container for L2VPN service";
    }
    description
      "Container for VPN services.";
      tailf:info "Container for VPN services.";
  }


  // NSO ADDITION START
  container l2nm-actions {
    tailf:action cleanup {
      tailf:actionpoint ietf-l2vpn-nm-cleanup;
      tailf:info "Clean up L2NM service configuration and operational data";
      description "Clean up L2NM service configuration and operational data";
      input {
        leaf service {
          type string;
          mandatory true;
        }
        leaf no-networking {
          type boolean;
          mandatory true;
        }
        leaf vpn-node {
          tailf:info "Clean up l2nm service configuration for given node only";
          description "Clean up l2nm service configuration for given node only";
          type leafref {
            tailf:no-leafref-check;
            path "/ncs:devices/lsa-utils:lsa/lsa-utils:dispatch-map/lsa-utils:device/lsa-utils:name";
          }
        }
      }
      output {
        leaf success {
          type boolean;
          mandatory true;
        }
        leaf detail {
          type string;
        }
      }
      tailf:confirm-text "########################\n" +
        "#        Warning       #\n" +
        "########################\n" +
        "You are about to forcefully cleanup a T-SDN service.\n" +
        "This will affect the deploying service and leave network device(s) & NSO out-of-sync (for no-networking=true).\n" +
        "Are you sure you want to proceed?" {
          tailf:confirm-default false;
      }
    }

    tailf:action internal-plan-change-handler {
      tailf:hidden full;
      tailf:actionpoint ietf-l2vpn-nm-internal-plan-change-handler;
      input {
        uses kicker:action-input-params;
      }
      output {
      }
    }

    tailf:action error-recovery {
      tailf:actionpoint ietf-l2vpn-nm-fp-error-recovery;
      tailf:info "Action to recover a service during create/update/delete from a transient failures
                  like device connection issues once the device is reachable again.
                  For create/update failures, this action issues a sync on the device
                  & redeploys the service with reconcile option.
                  For delete failures, this action issues a sync on the device &
                  redeploys zombie services.";
      description "Action to recover a service during create/update/delete from a transient failures
                  like device connection issues once the device is reachable again.
                  For create/update failures, this action issues a sync on the device
                  & redeploys the service with reconcile option.
                  For delete failures, this action issues a sync on the device &
                  redeploys zombie services.";
      input {
        leaf service {
          tailf:info "Service to recover";
          description "Service to recover";
          type string;
          mandatory true;
        }
        leaf vpn-node {
          tailf:info "Recover this vpn-node under given service.";
          description "Recover this vpn-node under given service.";
          type string;
        }
        leaf sync-direction {
          tailf:info "sync device with sync-from or sync-to";
          description "sync device with sync-from or sync-to";
          type enumeration {
            enum sync-from;
            enum sync-to;
          }
          mandatory true;
        }
      }
      output {
        leaf success {
          type boolean;
          mandatory true;
        }
        leaf detail {
          type string;
        }
      }
      tailf:confirm-text "########################\n" +
        "#        Warning       #\n" +
        "########################\n" +
        "You are about to recover a T-SDN service.\n" +
        "This will issue a sync on the device.\n" +
        "Are you sure you want to proceed?" {
          tailf:confirm-default false;
      }
    }
  }

  augment /l2vpn-ntw/vpn-services/vpn-service-plan/plan {
    uses tsdn-core-fp-common:status-code-plan-augmentation;
  }

  augment /l2vpn-ntw/vpn-services/vpn-service-plan/plan-history {
    uses tsdn-core-fp-common:status-code-plan-augmentation;
  }

  augment /l2vpn-ntw/vpn-services/vpn-service-plan/plan/component {
    uses tsdn-core-fp-common:status-code-component-augmentation;
    uses tsdn-core-fp-common:static-config-redeploy-indicator-component-augmentation;
  }

  augment /l2vpn-ntw/vpn-services/vpn-service-plan/plan-history/plan/component {
    uses tsdn-core-fp-common:status-code-component-augmentation;
    uses tsdn-core-fp-common:static-config-redeploy-indicator-component-augmentation;
  }
}
