module tapi-virtual-network {
  // Generated by yanger -t ncs
  tailf:mount-id "onf-tapi-nc-2.0:onf-tapi-nc-2.0";
  tailf:ncs-device-type "netconf";

  namespace "urn:onf:otcc:yang:tapi-virtual-network";
  prefix tapi-virtual-network;

  import tapi-topology {
    prefix tapi-topology;
  }
  import tapi-common {
    prefix tapi-common;
  }
  import tailf-common {
    prefix tailf;
  }
  import tailf-ncs {
    prefix ncs;
  }

  organization
    "ONF OTCC (Open Transport Configuration & Control) Project";
  contact
    "
     Project Web: <https://wiki.opennetworking.org/display/OTCC/TAPI>
     Project List: <mailto:transport-api@opennetworking.org>
     Editor: Karthik Sethuraman <mailto:karthik.sethuraman@necam.com>
     Andrea Mazzini <mailto:andrea.mazzini@nokia.com>
     Arturo Mayoral <mailto:arturo.mayoral@telefonica.com>
     Nigel Davis <mailto:ndavis@ciena.com>";
  description
    "
     This module contains TAPI Virtual Network Model definitions.
     Source: TapiVirtualNetwork.uml
     - The TAPI YANG models included in this TAPI release are a *normative* part of the TAPI SDK.
     - The YANG specifications have been generated from the corresponding UML model using the [ONF EAGLE UML2YANG mapping tool]
     <https://github.com/OpenNetworkingFoundation/EagleUmlYang>
     and further edited manually to comply with the [ONF IISOMI UML2YANG mapping guidelines]
     <https://wiki.opennetworking.org/display/OIMT/UML+-+YANG+Guidelines>
     - Status of YANG model artifacts can be determined by referring to the corresponding UML artifacts.
     As described in the UML models, some artifacts are considered *experimental*, and thus the corresponding YANG artifacts.
     - The ONF TAPI release process does not guarantee backward compatibility of YANG models across major versions of TAPI releases.
     The YANG model backward compatibility criteria are outlined in section 11 of <https://tools.ietf.org/html/rfc7950>.
     YANG models included in this release may not be backward compatible with previous TAPI releases.
     Copyright (c) 2018 Open Networking Foundation (ONF). All rights reserved.
     License: This module is distributed under the Apache License 2.0.";

  revision 2020-06-16 {
    description
      "ONF Transport API version 2.1.3.
       - schedule type changed to tapi-common:time-range.
       Changes included in this TAPI release (v2.1.3) are listed in
       <https://github.com/OpenNetworkingFoundation/TAPI/blob/develop_v2_1/CHANGE_LOG/change-log.2.1.3.md>";
    reference
      "ONF-TR-527, ONF-TR-512, ONF-TR-531, RFC 7950, RFC 6087 and ONF TAPI UML model
       <https://github.com/OpenNetworkingFoundation/TAPI/tree/v2.1.0/UML>";
  }
  revision 2019-07-16 {
    description
      "ONF Transport API version 2.1.2.
       Changes included in this TAPI release (v2.1.2) are listed in
       <https://github.com/OpenNetworkingFoundation/TAPI/blob/develop_v2_1/CHANGE_LOG/change-log.2.1.2.md>";
    reference
      "ONF-TR-527, ONF-TR-512, ONF-TR-531, RFC 7950, RFC 6087 and ONF TAPI UML model
       <https://github.com/OpenNetworkingFoundation/TAPI/tree/v2.1.0/UML>";
  }
  revision 2018-12-10 {
    description
      "ONF Transport API version 2.1.1.
       Changes included in this TAPI release (v2.1.1) are listed in
       <https://github.com/OpenNetworkingFoundation/TAPI/blob/develop/CHANGE_LOG/change-log.2.1.1.md>";
    reference
      "ONF-TR-527, ONF-TR-512, ONF-TR-531, RFC 7950, RFC 6087 and ONF TAPI UML model
       <https://github.com/OpenNetworkingFoundation/TAPI/tree/v2.1.0/UML>";
  }
  revision 2018-10-16 {
    description
      "ONF Transport API version 2.1.0.
       Changes included in this TAPI release (v2.1.0) are listed in
       <https://github.com/OpenNetworkingFoundation/TAPI/blob/develop/CHANGE_LOG/change-log.2.1.0.md>";
    reference
      "ONF-TR-527, ONF-TR-512, ONF-TR-531, RFC 7950, RFC 6087 and ONF TAPI UML model
       <https://github.com/OpenNetworkingFoundation/TAPI/tree/v2.1.0/UML>";
  }
  revision 2018-03-07 {
    description
      "ONF Transport API version 2.0.2
       This YANG module has been generated from the TAPI UML Model using the IISOMI-Eagle xmi2yang mapping tool.
       Changes in this revision: <https://github.com/OpenNetworkingFoundation/TAPI/blob/develop/CHANGE_LOG/change-log.2.0.2.md>";
    reference
      "ONF-TR-527, ONF-TR-512, ONF-TR-531, RFC 6020, RFC 6087 and ONF TAPI UML model
       <https://github.com/OpenNetworkingFoundation/TAPI/tree/v2.0.2/UML>";
  }
  revision 2018-02-16 {
    description
      "ONF Transport API version 2.0.1
       This YANG module has been generated from the TAPI UML Model using the IISOMI-Eagle xmi2yang mapping tool.
       Changes in this revision: <https://github.com/OpenNetworkingFoundation/TAPI/blob/develop/CHANGE_LOG/change-log.2.0.1.md>";
    reference
      "ONF-TR-527, ONF-TR-512, ONF-TR-531, RFC 6020, RFC 6087 and ONF TAPI UML model
       <https://github.com/OpenNetworkingFoundation/TAPI/tree/v2.0.1/UML>";
  }
  revision 2018-01-02 {
    description
      "ONF Transport API version 2.0.0
       This YANG module has been generated from the TAPI UML Model using the IISOMI-Eagle xmi2yang mapping tool.
       Changes in this revision: <https://github.com/OpenNetworkingFoundation/TAPI/blob/develop/CHANGE_LOG/change-log.2.0.0.md>";
    reference
      "ONF-TR-527, ONF-TR-512, ONF-TR-531, RFC 6020, RFC 6087 and ONF TAPI UML model
       <https://github.com/OpenNetworkingFoundation/TAPI/tree/v2.0.0/UML>";
  }

  grouping ncs_template_virtual-nw-service-ref {
    leaf virtual-nw-service-uuid {
      type string;
      description
        "none";
    }
    description
      "none";
  }

  grouping ncs_template_virtual-network-constraint {
    // NCS drop config false container 'src-service-end-point'
    // NCS drop config false container 'sink-service-end-point'
    // NCS drop config false list 'diversity-exclusion'
    container requested-capacity {
      uses tapi-common:ncs_template_capacity;
      description
        "none";
    }
    leaf service-level {
      type string;
      description
        "An abstract value the meaning of which is mutually agreed – typically represents metrics such as - Class of service, priority, resiliency, availability";
    }
    leaf-list service-layer {
      // NCS patched for predictable order
      ordered-by user;
      type tapi-common:ncs_template_layer-protocol-name;
      description
        "none";
    }
    list cost-characteristic {
      // NCS patched for predictable order
      ordered-by user;
      key "cost-name";
      uses tapi-topology:ncs_template_cost-characteristic;
      description
        "The list of costs where each cost relates to some aspect of the TopologicalEntity.";
    }
    list latency-characteristic {
      // NCS patched for predictable order
      ordered-by user;
      key "traffic-property-name";
      uses tapi-topology:ncs_template_latency-characteristic;
      description
        "The effect on the latency of a queuing process. This only has significant effect for packet based systems and has a complex characteristic.";
    }
    uses tapi-common:ncs_template_local-class;
    description
      "none";
  }

  grouping ncs_template_virtual-network-service {
    // NCS drop config false container topology
    list end-point {
      // NCS patched for predictable order
      ordered-by user;
      key "local-id";
      // NCS drop min-elements statement
      uses ncs_template_virtual-network-service-end-point;
      description
        "none";
    }
    list vnw-constraint {
      // NCS patched for predictable order
      ordered-by user;
      key "local-id";
      // NCS drop min-elements statement
      uses ncs_template_virtual-network-constraint;
      description
        "none";
    }
    container schedule {
      uses tapi-common:ncs_template_time-range;
      description
        "none";
    }
    container state {
      uses tapi-common:ncs_template_admin-state-pac;
      description
        "none";
    }
    leaf-list layer-protocol-name {
      // NCS patched for predictable order
      ordered-by user;
      type tapi-common:ncs_template_layer-protocol-name;
      // NCS drop min-elements statement
      description
        "none";
    }
    uses tapi-common:ncs_template_service-spec;
    description
      "The ForwardingConstruct (FC) object class models enabled potential for forwarding between two or more LTPs and like the LTP supports any transport protocol including all circuit and packet forms.
       At the lowest level of recursion, a FC represents a cross-connection within an NE.";
  }

  grouping ncs_template_virtual-network-service-end-point {
    // NCS drop config false container 'service-interface-point'
    // NCS drop config false leaf role
    // NCS drop config false leaf direction
    // NCS drop config false leaf 'service-layer'
    uses tapi-common:ncs_template_local-class;
    description
      "The association of the FC to LTPs is made via EndPoints.
       The EndPoint (EP) object class models the access to the FC function.
       The traffic forwarding between the associated EPs of the FC depends upon the type of FC and may be associated with FcSwitch object instances.
       In cases where there is resilience the EndPoint may convey the resilience role of the access to the FC.
       It can represent a protected (resilient/reliable) point or a protecting (unreliable working or protection) point.
       The EP replaces the Protection Unit of a traditional protection model.
       The ForwadingConstruct can be considered as a component and the EndPoint as a Port on that component";
  }

  grouping ncs_template_virtual-network-context {
    list virtual-nw-service {
      // NCS patched for predictable order
      ordered-by user;
      key "uuid";
      uses ncs_template_virtual-network-service;
      description
        "none";
    }
    description
      "none";
  }

  grouping ncs_rpc_notif_virtual-nw-service-ref {
    leaf virtual-nw-service-uuid {
      type string;
      description
        "none";
    }
    description
      "none";
  }

  grouping ncs_rpc_notif_virtual-network-constraint {
    container src-service-end-point {
      uses tapi-common:ncs_rpc_notif_service-interface-point-ref;
      config false;
      description
        "none";
    }
    container sink-service-end-point {
      uses tapi-common:ncs_rpc_notif_service-interface-point-ref;
      config false;
      description
        "none";
    }
    list diversity-exclusion {
      uses ncs_rpc_notif_virtual-nw-service-ref;
      key "virtual-nw-service-uuid";
      config false;
      description
        "none";
    }
    container requested-capacity {
      uses tapi-common:ncs_rpc_notif_capacity;
      description
        "none";
    }
    leaf service-level {
      type string;
      description
        "An abstract value the meaning of which is mutually agreed – typically represents metrics such as - Class of service, priority, resiliency, availability";
    }
    leaf-list service-layer {
      type tapi-common:ncs_rpc_notif_layer-protocol-name;
      description
        "none";
    }
    list cost-characteristic {
      key "cost-name";
      uses tapi-topology:ncs_rpc_notif_cost-characteristic;
      description
        "The list of costs where each cost relates to some aspect of the TopologicalEntity.";
    }
    list latency-characteristic {
      key "traffic-property-name";
      uses tapi-topology:ncs_rpc_notif_latency-characteristic;
      description
        "The effect on the latency of a queuing process. This only has significant effect for packet based systems and has a complex characteristic.";
    }
    uses tapi-common:ncs_rpc_notif_local-class;
    description
      "none";
  }

  grouping ncs_rpc_notif_virtual-network-service {
    container topology {
      uses tapi-topology:ncs_rpc_notif_topology-ref;
      config false;
      description
        "none";
    }
    list end-point {
      key "local-id";
      min-elements 2;
      uses ncs_rpc_notif_virtual-network-service-end-point;
      description
        "none";
    }
    list vnw-constraint {
      key "local-id";
      min-elements 1;
      uses ncs_rpc_notif_virtual-network-constraint;
      description
        "none";
    }
    container schedule {
      uses tapi-common:ncs_rpc_notif_time-range;
      description
        "none";
    }
    container state {
      uses tapi-common:ncs_rpc_notif_admin-state-pac;
      description
        "none";
    }
    leaf-list layer-protocol-name {
      type tapi-common:ncs_rpc_notif_layer-protocol-name;
      min-elements 1;
      description
        "none";
    }
    uses tapi-common:ncs_rpc_notif_service-spec;
    description
      "The ForwardingConstruct (FC) object class models enabled potential for forwarding between two or more LTPs and like the LTP supports any transport protocol including all circuit and packet forms.
       At the lowest level of recursion, a FC represents a cross-connection within an NE.";
  }

  grouping ncs_rpc_notif_virtual-network-service-end-point {
    container service-interface-point {
      uses tapi-common:ncs_rpc_notif_service-interface-point-ref;
      config false;
      description
        "none";
    }
    leaf role {
      type tapi-common:ncs_rpc_notif_port-role;
      config false;
      description
        "Each EP of the FC has a role (e.g., working, protection, protected, symmetric, hub, spoke, leaf, root)  in the context of the FC with respect to the FC function. ";
    }
    leaf direction {
      type tapi-common:ncs_rpc_notif_port-direction;
      config false;
      description
        "The orientation of defined flow at the EndPoint.";
    }
    leaf service-layer {
      type tapi-common:ncs_rpc_notif_layer-protocol-name;
      config false;
      description
        "none";
    }
    uses tapi-common:ncs_rpc_notif_local-class;
    description
      "The association of the FC to LTPs is made via EndPoints.
       The EndPoint (EP) object class models the access to the FC function.
       The traffic forwarding between the associated EPs of the FC depends upon the type of FC and may be associated with FcSwitch object instances.
       In cases where there is resilience the EndPoint may convey the resilience role of the access to the FC.
       It can represent a protected (resilient/reliable) point or a protecting (unreliable working or protection) point.
       The EP replaces the Protection Unit of a traditional protection model.
       The ForwadingConstruct can be considered as a component and the EndPoint as a Port on that component";
  }

  grouping ncs_rpc_notif_virtual-network-context {
    list virtual-nw-service {
      key "uuid";
      uses ncs_rpc_notif_virtual-network-service;
      description
        "none";
    }
    description
      "none";
  }

  grouping live_ncs_virtual-nw-service-ref {
    leaf virtual-nw-service-uuid {
      type leafref {
        path "/ncs:devices/ncs:device/ncs:live-status/tapi-common:context/tapi-virtual-network:virtual-network-context/tapi-virtual-network:virtual-nw-service/tapi-virtual-network:uuid" {
          tailf:xpath-root 3;
        }
      }
      description
        "none";
    }
    description
      "none";
  }

  grouping live_ncs_virtual-network-constraint {
    container src-service-end-point {
      uses tapi-common:live_ncs_service-interface-point-ref;
      description
        "none";
    }
    container sink-service-end-point {
      uses tapi-common:live_ncs_service-interface-point-ref;
      description
        "none";
    }
    list diversity-exclusion {
      uses live_ncs_virtual-nw-service-ref;
      key "virtual-nw-service-uuid";
      description
        "none";
    }
    container requested-capacity {
      uses tapi-common:live_ncs_capacity;
      description
        "none";
    }
    leaf service-level {
      type string;
      description
        "An abstract value the meaning of which is mutually agreed – typically represents metrics such as - Class of service, priority, resiliency, availability";
    }
    leaf-list service-layer {
      type tapi-common:live_ncs_layer-protocol-name;
      description
        "none";
    }
    list cost-characteristic {
      key "cost-name";
      uses tapi-topology:live_ncs_cost-characteristic;
      description
        "The list of costs where each cost relates to some aspect of the TopologicalEntity.";
    }
    list latency-characteristic {
      key "traffic-property-name";
      uses tapi-topology:live_ncs_latency-characteristic;
      description
        "The effect on the latency of a queuing process. This only has significant effect for packet based systems and has a complex characteristic.";
    }
    uses tapi-common:live_ncs_local-class;
    description
      "none";
  }

  grouping live_ncs_virtual-network-service {
    container topology {
      uses tapi-topology:live_ncs_topology-ref;
      description
        "none";
    }
    list end-point {
      key "local-id";
      // NCS drop min-elements statement
      uses live_ncs_virtual-network-service-end-point;
      description
        "none";
    }
    list vnw-constraint {
      key "local-id";
      // NCS drop min-elements statement
      uses live_ncs_virtual-network-constraint;
      description
        "none";
    }
    container schedule {
      uses tapi-common:live_ncs_time-range;
      description
        "none";
    }
    container state {
      uses tapi-common:live_ncs_admin-state-pac;
      description
        "none";
    }
    leaf-list layer-protocol-name {
      type tapi-common:live_ncs_layer-protocol-name;
      // NCS drop min-elements statement
      description
        "none";
    }
    uses tapi-common:live_ncs_service-spec;
    description
      "The ForwardingConstruct (FC) object class models enabled potential for forwarding between two or more LTPs and like the LTP supports any transport protocol including all circuit and packet forms.
       At the lowest level of recursion, a FC represents a cross-connection within an NE.";
  }

  grouping live_ncs_virtual-network-service-end-point {
    container service-interface-point {
      uses tapi-common:live_ncs_service-interface-point-ref;
      description
        "none";
    }
    leaf role {
      type tapi-common:live_ncs_port-role;
      description
        "Each EP of the FC has a role (e.g., working, protection, protected, symmetric, hub, spoke, leaf, root)  in the context of the FC with respect to the FC function. ";
    }
    leaf direction {
      type tapi-common:live_ncs_port-direction;
      description
        "The orientation of defined flow at the EndPoint.";
    }
    leaf service-layer {
      type tapi-common:live_ncs_layer-protocol-name;
      description
        "none";
    }
    uses tapi-common:live_ncs_local-class;
    description
      "The association of the FC to LTPs is made via EndPoints.
       The EndPoint (EP) object class models the access to the FC function.
       The traffic forwarding between the associated EPs of the FC depends upon the type of FC and may be associated with FcSwitch object instances.
       In cases where there is resilience the EndPoint may convey the resilience role of the access to the FC.
       It can represent a protected (resilient/reliable) point or a protecting (unreliable working or protection) point.
       The EP replaces the Protection Unit of a traditional protection model.
       The ForwadingConstruct can be considered as a component and the EndPoint as a Port on that component";
  }

  grouping live_ncs_virtual-network-context {
    list virtual-nw-service {
      key "uuid";
      uses live_ncs_virtual-network-service;
      description
        "none";
    }
    description
      "none";
  }

  grouping virtual-nw-service-ref {
    leaf virtual-nw-service-uuid {
      type leafref {
        path "/ncs:devices/ncs:device/ncs:config/tapi-common:context/tapi-virtual-network:virtual-network-context/tapi-virtual-network:virtual-nw-service/tapi-virtual-network:uuid" {
          tailf:xpath-root 3;
        }
      }
      description
        "none";
    }
    description
      "none";
  }

  grouping virtual-network-constraint {
    // NCS drop config false container 'src-service-end-point'
    // NCS drop config false container 'sink-service-end-point'
    // NCS drop config false list 'diversity-exclusion'
    container requested-capacity {
      uses tapi-common:capacity;
      description
        "none";
    }
    leaf service-level {
      type string;
      description
        "An abstract value the meaning of which is mutually agreed – typically represents metrics such as - Class of service, priority, resiliency, availability";
    }
    leaf-list service-layer {
      type tapi-common:layer-protocol-name;
      description
        "none";
    }
    list cost-characteristic {
      key "cost-name";
      uses tapi-topology:cost-characteristic;
      description
        "The list of costs where each cost relates to some aspect of the TopologicalEntity.";
    }
    list latency-characteristic {
      key "traffic-property-name";
      uses tapi-topology:latency-characteristic;
      description
        "The effect on the latency of a queuing process. This only has significant effect for packet based systems and has a complex characteristic.";
    }
    uses tapi-common:local-class;
    description
      "none";
  }

  grouping virtual-network-service {
    // NCS drop config false container topology
    list end-point {
      key "local-id";
      min-elements 2;
      uses virtual-network-service-end-point;
      description
        "none";
    }
    list vnw-constraint {
      key "local-id";
      min-elements 1;
      uses virtual-network-constraint;
      description
        "none";
    }
    container schedule {
      uses tapi-common:time-range;
      description
        "none";
    }
    container state {
      uses tapi-common:admin-state-pac;
      description
        "none";
    }
    leaf-list layer-protocol-name {
      type tapi-common:layer-protocol-name;
      min-elements 1;
      description
        "none";
    }
    uses tapi-common:service-spec;
    description
      "The ForwardingConstruct (FC) object class models enabled potential for forwarding between two or more LTPs and like the LTP supports any transport protocol including all circuit and packet forms.
       At the lowest level of recursion, a FC represents a cross-connection within an NE.";
  }

  grouping virtual-network-service-end-point {
    // NCS drop config false container 'service-interface-point'
    // NCS drop config false leaf role
    // NCS drop config false leaf direction
    // NCS drop config false leaf 'service-layer'
    uses tapi-common:local-class;
    description
      "The association of the FC to LTPs is made via EndPoints.
       The EndPoint (EP) object class models the access to the FC function.
       The traffic forwarding between the associated EPs of the FC depends upon the type of FC and may be associated with FcSwitch object instances.
       In cases where there is resilience the EndPoint may convey the resilience role of the access to the FC.
       It can represent a protected (resilient/reliable) point or a protecting (unreliable working or protection) point.
       The EP replaces the Protection Unit of a traditional protection model.
       The ForwadingConstruct can be considered as a component and the EndPoint as a Port on that component";
  }

  grouping virtual-network-context {
    list virtual-nw-service {
      key "uuid";
      uses virtual-network-service;
      description
        "none";
    }
    description
      "none";
  }

  augment "/ncs:devices/ncs:device/ncs:rpc" {
    container rpc-get-virtual-network-service-list {
      tailf:ncs-device-type "netconf";
      tailf:display-when "not(../../ncs:module) or ../../ncs:module[ncs:name='tapi-virtual-network']";
      tailf:action get-virtual-network-service-list {
        tailf:actionpoint ncsproxy {
          tailf:internal;
        }
        description
          "none";
        output {
          list service {
            uses ncs_rpc_notif_virtual-network-service;
            description
              "none";
          }
        }
      }
    }
  }
  augment "/ncs:devices/ncs:device-group/ncs:ned-id/ncs:rpc" {
    container rpc-get-virtual-network-service-list {
      tailf:ncs-device-type "netconf";
      tailf:display-when "../../ncs:id = 'onf-tapi-nc-2.0:onf-tapi-nc-2.0'";
      tailf:action get-virtual-network-service-list {
        tailf:actionpoint ncsproxy {
          tailf:internal;
        }
        description
          "none";
        output {
          container "device" {
            leaf "name" {
              type string;
            }
            leaf "info" {
              type string;
            }
            container "result" {
              list service {
                uses ncs_rpc_notif_virtual-network-service;
                description
                  "none";
              }
            }
          }
        }
      }
    }
  }
  augment "/ncs:devices/ncs:device/ncs:rpc" {
    container rpc-get-virtual-network-service-details {
      tailf:ncs-device-type "netconf";
      tailf:display-when "not(../../ncs:module) or ../../ncs:module[ncs:name='tapi-virtual-network']";
      tailf:action get-virtual-network-service-details {
        tailf:actionpoint ncsproxy {
          tailf:internal;
        }
        description
          "none";
        input {
          leaf service-id-or-name {
            type string;
            description
              "none";
          }
        }
        output {
          container service {
            uses ncs_rpc_notif_virtual-network-service;
            description
              "none";
          }
        }
      }
    }
  }
  augment "/ncs:devices/ncs:device-group/ncs:ned-id/ncs:rpc" {
    container rpc-get-virtual-network-service-details {
      tailf:ncs-device-type "netconf";
      tailf:display-when "../../ncs:id = 'onf-tapi-nc-2.0:onf-tapi-nc-2.0'";
      tailf:action get-virtual-network-service-details {
        tailf:actionpoint ncsproxy {
          tailf:internal;
        }
        description
          "none";
        input {
          leaf service-id-or-name {
            type string;
            description
              "none";
          }
        }
        output {
          container "device" {
            leaf "name" {
              type string;
            }
            leaf "info" {
              type string;
            }
            container "result" {
              container service {
                uses ncs_rpc_notif_virtual-network-service;
                description
                  "none";
              }
            }
          }
        }
      }
    }
  }
  augment "/ncs:devices/ncs:device/ncs:rpc" {
    container rpc-delete-virtual-network-service {
      tailf:ncs-device-type "netconf";
      tailf:display-when "not(../../ncs:module) or ../../ncs:module[ncs:name='tapi-virtual-network']";
      tailf:action delete-virtual-network-service {
        tailf:actionpoint ncsproxy {
          tailf:internal;
        }
        description
          "none";
        input {
          leaf service-id-or-name {
            type string;
            description
              "none";
          }
        }
        output {
          container service {
            uses ncs_rpc_notif_virtual-network-service;
            description
              "none";
          }
        }
      }
    }
  }
  augment "/ncs:devices/ncs:device-group/ncs:ned-id/ncs:rpc" {
    container rpc-delete-virtual-network-service {
      tailf:ncs-device-type "netconf";
      tailf:display-when "../../ncs:id = 'onf-tapi-nc-2.0:onf-tapi-nc-2.0'";
      tailf:action delete-virtual-network-service {
        tailf:actionpoint ncsproxy {
          tailf:internal;
        }
        description
          "none";
        input {
          leaf service-id-or-name {
            type string;
            description
              "none";
          }
        }
        output {
          container "device" {
            leaf "name" {
              type string;
            }
            leaf "info" {
              type string;
            }
            container "result" {
              container service {
                uses ncs_rpc_notif_virtual-network-service;
                description
                  "none";
              }
            }
          }
        }
      }
    }
  }
  augment "/ncs:devices/ncs:device/ncs:rpc" {
    container rpc-create-virtual-network-service {
      tailf:ncs-device-type "netconf";
      tailf:display-when "not(../../ncs:module) or ../../ncs:module[ncs:name='tapi-virtual-network']";
      tailf:action create-virtual-network-service {
        tailf:actionpoint ncsproxy {
          tailf:internal;
        }
        description
          "none";
        input {
          list sep {
            min-elements 2;
            uses ncs_rpc_notif_virtual-network-service-end-point;
            description
              "none";
          }
          container vnw-constraint {
            uses ncs_rpc_notif_virtual-network-constraint;
            description
              "none";
          }
          container conn-schedule {
            uses tapi-common:ncs_rpc_notif_time-range;
            description
              "none";
          }
        }
        output {
          container service {
            uses ncs_rpc_notif_virtual-network-service;
            description
              "none";
          }
        }
      }
    }
  }
  augment "/ncs:devices/ncs:device-group/ncs:ned-id/ncs:rpc" {
    container rpc-create-virtual-network-service {
      tailf:ncs-device-type "netconf";
      tailf:display-when "../../ncs:id = 'onf-tapi-nc-2.0:onf-tapi-nc-2.0'";
      tailf:action create-virtual-network-service {
        tailf:actionpoint ncsproxy {
          tailf:internal;
        }
        description
          "none";
        input {
          list sep {
            min-elements 2;
            uses ncs_rpc_notif_virtual-network-service-end-point;
            description
              "none";
          }
          container vnw-constraint {
            uses ncs_rpc_notif_virtual-network-constraint;
            description
              "none";
          }
          container conn-schedule {
            uses tapi-common:ncs_rpc_notif_time-range;
            description
              "none";
          }
        }
        output {
          container "device" {
            leaf "name" {
              type string;
            }
            leaf "info" {
              type string;
            }
            container "result" {
              container service {
                uses ncs_rpc_notif_virtual-network-service;
                description
                  "none";
              }
            }
          }
        }
      }
    }
  }
  augment "/ncs:devices/ncs:template/ncs:ned-id/ncs:config/tapi-common:context" {
    container virtual-network-context {
      uses ncs_template_virtual-network-context;
      description
        "Augments the base TAPI Context with VirtualNetworkService information";
    }
    description
      "Augments the base TAPI Context with VirtualNetworkService information";
  }
  augment "/ncs:devices/ncs:device/ncs:live-status/tapi-common:context" {
    container virtual-network-context {
      tailf:ncs-device-type "netconf";
      tailf:display-when "not(../../../ncs:module) or ../../../ncs:module[ncs:name='tapi-virtual-network'] or (../../../ncs:live-status-protocol[not(ncs:capability)]) or (../../../ncs:live-status-protocol/ncs:capability/ncs:module[.='tapi-virtual-network'])";
      uses live_ncs_virtual-network-context;
      description
        "Augments the base TAPI Context with VirtualNetworkService information";
    }
    description
      "Augments the base TAPI Context with VirtualNetworkService information";
  }
  augment "/ncs:devices/ncs:device/ncs:config/tapi-common:context" {
    container virtual-network-context {
      tailf:ncs-device-type "netconf";
      tailf:display-when "not(../../../ncs:module) or ../../../ncs:module[ncs:name='tapi-virtual-network']";
      uses virtual-network-context;
      description
        "Augments the base TAPI Context with VirtualNetworkService information";
    }
    description
      "Augments the base TAPI Context with VirtualNetworkService information";
  }
}
