module tailf-aaa {
  // Generated by yanger -t ncs
  tailf:mount-id "onf-tapi-nc-2.0:onf-tapi-nc-2.0";
  tailf:ncs-device-type "netconf";

  namespace "http://tail-f.com/ns/aaa/1.1";
  prefix aaa;
  // NCS drop tailf:id

  import ietf-netconf-acm {
    prefix nacm;
  }
  import iana-crypt-hash {
    prefix ianach;
  }
  import tailf-common {
    prefix tailf;
  }
  import tailf-ncs {
    prefix ncs;
  }

  organization
    "Tail-f Systems";
  description
    "This module defines the Tail-f AAA data model.";

  revision 2022-01-25 {
    description
      "Released as part of ConfD-7.7.1 / NCS-5.7.1.

       Updated range for idle-timeout type.";
  }
  revision 2018-09-12 {
    description
      "Released as part of ConfD-6.5.7 / NSO-4.5.7.

       Added tailf:suppress-echo for /aaa/authentication/users/user/password.";
  }
  revision 2015-06-16 {
    description
      "Released as part of ConfD-6.0 / NSO-4.0.

       Added /aaa/authentication/users/user/change-password action.";
  }
  revision 2014-08-29 {
    description
      "Released as part of ConfD-5.2.1 / NCS-3.2.1.

       Removed max-elements restriction on /aaa/authentication/users/user.";
  }
  revision 2014-06-30 {
    description
      "Released as part of ConfD-5.2 / NCS-3.2.

       Changed passwdStr typedef to use ianach:crypt-hash instead of
       tailf:md5-digest-string.";
  }
  revision 2013-03-07 {
    description
      "Released as part of ConfD-4.2.

       Added nacm:default-deny-all extension for /aaa and /user, and
       nacm:default-deny-write extension for /alias and /session.";
  }
  revision 2012-11-08 {
    description
      "Released as part of ConfD-4.1.

       Removed /aaa/authentication/groups and /aaa/authorization,
       since this functionality is modeled in
       ietf-netconf-acm.yang as augmented by tailf-acm.yang.";
  }
  revision 2011-09-22 {
    description
      "Released as part of ConfD-3.7.";
  }
  revision 2010-06-17 {
    description
      "Released as part of ConfD-3.3.";
  }
  revision 2010-04-22 {
    description
      "Released as part of ConfD-3.2.1.";
  }
  revision 2010-03-18 {
    description
      "Released as part of ConfD-3.2.";
  }

  typedef ncs_template_history {
    type string;
  }

  typedef ncs_template_idle-timeout {
    type string;
  }

  typedef ncs_template_display-level {
    type string;
  }

  typedef ncs_template_passwdStr {
    type string;
  }

  typedef ncs_template_levelInt {
    type string;
  }

  typedef ncs_template_modeStr {
    type string;
  }

  typedef ncs_template_builtinModes {
    type string;
  }

  typedef ncs_rpc_notif_history {
    type uint64 {
      range "0 .. 8192";
    }
  }

  typedef ncs_rpc_notif_idle-timeout {
    type uint64 {
      range "0 .. 4294967";
    }
  }

  typedef ncs_rpc_notif_display-level {
    type uint64 {
      range "1 .. 64";
    }
  }

  typedef ncs_rpc_notif_passwdStr {
    type ianach:crypt-hash;
  }

  typedef ncs_rpc_notif_levelInt {
    type int32 {
      range "0 .. 15";
    }
  }

  typedef ncs_rpc_notif_modeStr {
    type union {
      type string;
      type ncs_rpc_notif_builtinModes;
    }
  }

  typedef ncs_rpc_notif_builtinModes {
    type enumeration {
      enum "exec";
      enum "configure";
    }
  }

  typedef live_ncs_history {
    type uint64 {
      range "0 .. 8192";
    }
  }

  typedef live_ncs_idle-timeout {
    type uint64 {
      range "0 .. 4294967";
    }
  }

  typedef live_ncs_display-level {
    type uint64 {
      range "1 .. 64";
    }
  }

  typedef live_ncs_passwdStr {
    type ianach:crypt-hash;
  }

  typedef live_ncs_levelInt {
    type int32 {
      range "0 .. 15";
    }
  }

  typedef live_ncs_modeStr {
    type union {
      type string;
      type live_ncs_builtinModes;
    }
  }

  typedef live_ncs_builtinModes {
    type enumeration {
      enum "exec";
      enum "configure";
    }
  }

  typedef history {
    type uint64 {
      range "0 .. 8192";
    }
  }

  typedef idle-timeout {
    type uint64 {
      range "0 .. 4294967";
    }
  }

  typedef display-level {
    type uint64 {
      range "1 .. 64";
    }
  }

  typedef passwdStr {
    type ianach:crypt-hash;
  }

  typedef levelInt {
    type int32 {
      range "0 .. 15";
    }
  }

  typedef modeStr {
    type union {
      type string;
      type builtinModes;
    }
  }

  typedef builtinModes {
    type enumeration {
      enum "exec";
      enum "configure";
    }
  }

  grouping ncs_template_session-params {
    leaf complete-on-space {
      type string;
    }
    leaf ignore-leading-space {
      type string;
    }
    leaf idle-timeout {
      type ncs_template_idle-timeout;
    }
    leaf paginate {
      type string;
    }
    leaf history {
      type ncs_template_history;
    }
    leaf autowizard {
      type string;
    }
    leaf show-defaults {
      type string;
    }
    leaf display-level {
      type ncs_template_display-level;
    }
    leaf prompt1 {
      type string;
    }
    leaf prompt2 {
      type string;
    }
    leaf devtools {
      type string;
    }
  }

  grouping ncs_rpc_notif_session-params {
    leaf complete-on-space {
      type boolean;
      tailf:info
        "Enable/disable completion on space";
    }
    leaf ignore-leading-space {
      type boolean;
      tailf:info
        "Ignore leading whitespace";
    }
    leaf idle-timeout {
      type ncs_rpc_notif_idle-timeout;
      tailf:info
        "CLI idle-timeout in seconds";
    }
    leaf paginate {
      type boolean;
      tailf:info
        "Paginate output from CLI commands";
    }
    leaf history {
      type ncs_rpc_notif_history;
      tailf:info
        "History size";
    }
    leaf autowizard {
      type boolean;
      tailf:info
        "Automatically query user for mandatory elems";
    }
    leaf show-defaults {
      type boolean;
      tailf:info
        "Show default values when showing the configuration";
    }
    leaf display-level {
      type ncs_rpc_notif_display-level;
      tailf:info
        "Max depth to show when displaying configuration";
    }
    leaf prompt1 {
      type string;
      tailf:info
        "Prompt for operational mode";
    }
    leaf prompt2 {
      type string;
      tailf:info
        "Prompt for configure mode";
    }
    leaf devtools {
      type boolean;
      tailf:info
        "Enable/disable development tools";
    }
  }

  grouping live_ncs_session-params {
    leaf complete-on-space {
      type boolean;
      tailf:info
        "Enable/disable completion on space";
    }
    leaf ignore-leading-space {
      type boolean;
      tailf:info
        "Ignore leading whitespace";
    }
    leaf idle-timeout {
      type live_ncs_idle-timeout;
      tailf:info
        "CLI idle-timeout in seconds";
    }
    leaf paginate {
      type boolean;
      tailf:info
        "Paginate output from CLI commands";
    }
    leaf history {
      type live_ncs_history;
      tailf:info
        "History size";
    }
    leaf autowizard {
      type boolean;
      tailf:info
        "Automatically query user for mandatory elems";
    }
    leaf show-defaults {
      type boolean;
      tailf:info
        "Show default values when showing the configuration";
    }
    leaf display-level {
      type live_ncs_display-level;
      tailf:info
        "Max depth to show when displaying configuration";
    }
    leaf prompt1 {
      type string;
      tailf:info
        "Prompt for operational mode";
    }
    leaf prompt2 {
      type string;
      tailf:info
        "Prompt for configure mode";
    }
    leaf devtools {
      type boolean;
      tailf:info
        "Enable/disable development tools";
    }
  }

  grouping session-params {
    leaf complete-on-space {
      type boolean;
      tailf:info
        "Enable/disable completion on space";
    }
    leaf ignore-leading-space {
      type boolean;
      tailf:info
        "Ignore leading whitespace";
    }
    leaf idle-timeout {
      type idle-timeout;
      tailf:info
        "CLI idle-timeout in seconds";
    }
    leaf paginate {
      type boolean;
      tailf:info
        "Paginate output from CLI commands";
    }
    leaf history {
      type history;
      tailf:info
        "History size";
    }
    leaf autowizard {
      type boolean;
      tailf:info
        "Automatically query user for mandatory elems";
    }
    leaf show-defaults {
      type boolean;
      tailf:info
        "Show default values when showing the configuration";
    }
    leaf display-level {
      type display-level;
      tailf:info
        "Max depth to show when displaying configuration";
    }
    leaf prompt1 {
      type string;
      tailf:info
        "Prompt for operational mode";
    }
    leaf prompt2 {
      type string;
      tailf:info
        "Prompt for configure mode";
    }
    leaf devtools {
      type boolean;
      tailf:info
        "Enable/disable development tools";
    }
  }

  augment "/ncs:devices/ncs:device/ncs:config" {
    container aaa {
      tailf:ncs-device-type "netconf";
      tailf:display-when "not(../../ncs:module) or ../../ncs:module[ncs:name='tailf-aaa']";
      tailf:info
        "AAA management";
      nacm:default-deny-all;
      container authentication {
        tailf:info
          "User management";
        container users {
          tailf:info
            "List of local users";
          list user {
            key "name";
            leaf name {
              type string;
              tailf:info
                "Login name of the user";
            }
            leaf uid {
              type int32;
              mandatory true;
              tailf:info
                "User Identifier";
            }
            leaf gid {
              type int32;
              mandatory true;
              tailf:info
                "Group Identifier";
            }
            leaf password {
              type passwdStr;
              mandatory true;
              tailf:suppress-echo true;
            }
            leaf ssh_keydir {
              type string;
              mandatory true;
              tailf:info
                "Absolute path to directory where user's ssh keys
                 may be found";
            }
            leaf homedir {
              type string;
              mandatory true;
              tailf:info
                "Absolute path to user's home directory";
            }
            tailf:action change-password {
              tailf:actionpoint ncsproxy {
                tailf:internal;
              }
              tailf:info
                "Request password change";
              // NCS drop tailf:actionpoint
              input {
                leaf old-password {
                  type string;
                  mandatory true;
                  tailf:info
                    "Old password";
                  tailf:suppress-echo true;
                }
                leaf new-password {
                  type string;
                  mandatory true;
                  tailf:info
                    "New password";
                  tailf:suppress-echo true;
                }
                leaf confirm-password {
                  type string;
                  mandatory true;
                  tailf:info
                    "Confirm New password";
                  tailf:suppress-echo true;
                }
              }
            }
          }
        }
      }
      container ios {
        tailf:info
          "Specific IOS settings";
        presence "";
        list level {
          key "nr";
          min-elements 2;
          leaf nr {
            type levelInt;
          }
          leaf secret {
            type passwdStr;
          }
          leaf password {
            type passwdStr;
          }
          leaf prompt {
            type string;
            default "\\h# ";
          }
        }
        list privilege {
          key "mode";
          leaf mode {
            type modeStr;
          }
          list level {
            key "nr";
            min-elements 1;
            max-elements 15;
            leaf nr {
              type levelInt;
            }
            list command {
              key "name";
              leaf name {
                type string;
              }
            }
          }
        }
      }
    }
    list alias {
      tailf:ncs-device-type "netconf";
      tailf:display-when "not(../ncs:module) or ../ncs:module[ncs:name='tailf-aaa']";
      nacm:default-deny-write;
      key "name";
      tailf:info
        "Create command alias.";
      leaf name {
        type string;
        tailf:info
          "Name of the command alias. An alias name can be a single
           word or multiple words joined by a dash (-).";
      }
      leaf expansion {
        type string;
        mandatory true;
        tailf:info
          "Original command syntax. Valid abbreviations of the original
           command syntax can be entered for the command-syntax
           argument.";
      }
    }
    container session {
      tailf:ncs-device-type "netconf";
      tailf:display-when "not(../../ncs:module) or ../../ncs:module[ncs:name='tailf-aaa']";
      nacm:default-deny-write;
      uses session-params;
      presence "";
      tailf:info
        "Global default CLI session parameters";
    }
    list user {
      tailf:ncs-device-type "netconf";
      tailf:display-when "not(../ncs:module) or ../ncs:module[ncs:name='tailf-aaa']";
      tailf:info
        "User specific command aliases and default CLI session
         parameters";
      nacm:default-deny-all;
      key "name";
      leaf name {
        type string;
      }
      leaf description {
        type string;
        tailf:info
          "User description";
      }
      list alias {
        key "name";
        tailf:info
          "Create command alias.";
        leaf name {
          type string;
          tailf:info
            "Name of the command alias. An alias name can be a single
             word or multiple words joined by a dash (-).";
        }
        leaf expansion {
          type string;
          mandatory true;
          tailf:info
            "Original command syntax. Valid abbreviations of the original
             command syntax can be entered for the command-syntax
             argument.";
        }
      }
      container session {
        uses session-params;
        tailf:info
          "User specific default CLI session parameters";
      }
    }
  }
  augment "/ncs:devices/ncs:device/ncs:live-status" {
    container aaa {
      tailf:ncs-device-type "netconf";
      tailf:display-when "not(../../ncs:module) or ../../ncs:module[ncs:name='tailf-aaa'] or (../../ncs:live-status-protocol[not(ncs:capability)]) or (../../ncs:live-status-protocol/ncs:capability/ncs:module[.='tailf-aaa'])";
      tailf:info
        "AAA management";
      nacm:default-deny-all;
      container authentication {
        tailf:info
          "User management";
        container users {
          tailf:info
            "List of local users";
          list user {
            key "name";
            leaf name {
              type string;
              tailf:info
                "Login name of the user";
            }
            leaf uid {
              type int32;
              // NCS drop mandatory statement
              tailf:info
                "User Identifier";
            }
            leaf gid {
              type int32;
              // NCS drop mandatory statement
              tailf:info
                "Group Identifier";
            }
            leaf password {
              type live_ncs_passwdStr;
              // NCS drop mandatory statement
              tailf:suppress-echo true;
            }
            leaf ssh_keydir {
              type string;
              // NCS drop mandatory statement
              tailf:info
                "Absolute path to directory where user's ssh keys
                 may be found";
            }
            leaf homedir {
              type string;
              // NCS drop mandatory statement
              tailf:info
                "Absolute path to user's home directory";
            }
            tailf:action change-password {
              tailf:actionpoint ncsproxy {
                tailf:internal;
              }
              tailf:info
                "Request password change";
              // NCS drop tailf:actionpoint
              input {
                leaf old-password {
                  type string;
                  mandatory true;
                  tailf:info
                    "Old password";
                  tailf:suppress-echo true;
                }
                leaf new-password {
                  type string;
                  mandatory true;
                  tailf:info
                    "New password";
                  tailf:suppress-echo true;
                }
                leaf confirm-password {
                  type string;
                  mandatory true;
                  tailf:info
                    "Confirm New password";
                  tailf:suppress-echo true;
                }
              }
            }
          }
        }
      }
      container ios {
        tailf:info
          "Specific IOS settings";
        presence "";
        list level {
          key "nr";
          // NCS drop min-elements statement
          leaf nr {
            type live_ncs_levelInt;
          }
          leaf secret {
            type live_ncs_passwdStr;
          }
          leaf password {
            type live_ncs_passwdStr;
          }
          leaf prompt {
            type string;
            // NCS drop default statement
          }
        }
        list privilege {
          key "mode";
          leaf mode {
            type live_ncs_modeStr;
          }
          list level {
            key "nr";
            // NCS drop min-elements statement
            // NCS drop max-elements statement
            leaf nr {
              type live_ncs_levelInt;
            }
            list command {
              key "name";
              leaf name {
                type string;
              }
            }
          }
        }
      }
    }
    list alias {
      tailf:ncs-device-type "netconf";
      tailf:display-when "not(../ncs:module) or ../ncs:module[ncs:name='tailf-aaa'] or (../ncs:live-status-protocol[not(ncs:capability)]) or (../ncs:live-status-protocol/ncs:capability/ncs:module[.='tailf-aaa'])";
      nacm:default-deny-write;
      key "name";
      tailf:info
        "Create command alias.";
      leaf name {
        type string;
        tailf:info
          "Name of the command alias. An alias name can be a single
           word or multiple words joined by a dash (-).";
      }
      leaf expansion {
        type string;
        // NCS drop mandatory statement
        tailf:info
          "Original command syntax. Valid abbreviations of the original
           command syntax can be entered for the command-syntax
           argument.";
      }
    }
    container session {
      tailf:ncs-device-type "netconf";
      tailf:display-when "not(../../ncs:module) or ../../ncs:module[ncs:name='tailf-aaa'] or (../../ncs:live-status-protocol[not(ncs:capability)]) or (../../ncs:live-status-protocol/ncs:capability/ncs:module[.='tailf-aaa'])";
      nacm:default-deny-write;
      uses live_ncs_session-params;
      presence "";
      tailf:info
        "Global default CLI session parameters";
    }
    list user {
      tailf:ncs-device-type "netconf";
      tailf:display-when "not(../ncs:module) or ../ncs:module[ncs:name='tailf-aaa'] or (../ncs:live-status-protocol[not(ncs:capability)]) or (../ncs:live-status-protocol/ncs:capability/ncs:module[.='tailf-aaa'])";
      tailf:info
        "User specific command aliases and default CLI session
         parameters";
      nacm:default-deny-all;
      key "name";
      leaf name {
        type string;
      }
      leaf description {
        type string;
        tailf:info
          "User description";
      }
      list alias {
        key "name";
        tailf:info
          "Create command alias.";
        leaf name {
          type string;
          tailf:info
            "Name of the command alias. An alias name can be a single
             word or multiple words joined by a dash (-).";
        }
        leaf expansion {
          type string;
          // NCS drop mandatory statement
          tailf:info
            "Original command syntax. Valid abbreviations of the original
             command syntax can be entered for the command-syntax
             argument.";
        }
      }
      container session {
        uses live_ncs_session-params;
        tailf:info
          "User specific default CLI session parameters";
      }
    }
  }
  augment "/ncs:devices/ncs:template/ncs:ned-id/ncs:config" {
    container aaa {
      nacm:default-deny-all;
      container authentication {
        container users {
          list user {
            // NCS patched for predictable order
            ordered-by user;
            key "name";
            leaf name {
              type string;
            }
            leaf uid {
              type string;
              // NCS drop mandatory statement
            }
            leaf gid {
              type string;
              // NCS drop mandatory statement
            }
            leaf password {
              type ncs_template_passwdStr;
              // NCS drop mandatory statement
            }
            leaf ssh_keydir {
              type string;
              // NCS drop mandatory statement
            }
            leaf homedir {
              type string;
              // NCS drop mandatory statement
            }
          }
        }
      }
      container ios {
        presence "";
        list level {
          // NCS patched for predictable order
          ordered-by user;
          key "nr";
          // NCS drop min-elements statement
          leaf nr {
            type ncs_template_levelInt;
          }
          leaf secret {
            type ncs_template_passwdStr;
          }
          leaf password {
            type ncs_template_passwdStr;
          }
          leaf prompt {
            type string;
            // NCS drop default statement
          }
        }
        list privilege {
          // NCS patched for predictable order
          ordered-by user;
          key "mode";
          leaf mode {
            type ncs_template_modeStr;
          }
          list level {
            // NCS patched for predictable order
            ordered-by user;
            key "nr";
            // NCS drop min-elements statement
            // NCS drop max-elements statement
            leaf nr {
              type ncs_template_levelInt;
            }
            list command {
              // NCS patched for predictable order
              ordered-by user;
              key "name";
              leaf name {
                type string;
              }
            }
          }
        }
      }
    }
    list alias {
      // NCS patched for predictable order
      ordered-by user;
      nacm:default-deny-write;
      key "name";
      leaf name {
        type string;
      }
      leaf expansion {
        type string;
        // NCS drop mandatory statement
      }
    }
    container session {
      nacm:default-deny-write;
      uses ncs_template_session-params;
      presence "";
    }
    list user {
      // NCS patched for predictable order
      ordered-by user;
      nacm:default-deny-all;
      key "name";
      leaf name {
        type string;
      }
      leaf description {
        type string;
      }
      list alias {
        // NCS patched for predictable order
        ordered-by user;
        key "name";
        leaf name {
          type string;
        }
        leaf expansion {
          type string;
          // NCS drop mandatory statement
        }
      }
      container session {
        uses ncs_template_session-params;
      }
    }
  }
}
