module tapi-oam {
  // Generated by yanger -t ncs
  tailf:mount-id "onf-tapi-nc-2.0:onf-tapi-nc-2.0";
  tailf:ncs-device-type "netconf";

  namespace "urn:onf:otcc:yang:tapi-oam";
  prefix tapi-oam;

  import tapi-common {
    prefix tapi-common;
  }
  import tapi-connectivity {
    prefix tapi-connectivity;
  }
  import tapi-topology {
    prefix tapi-topology;
  }
  import tailf-common {
    prefix tailf;
  }
  import tailf-ncs {
    prefix ncs;
  }

  organization
    "ONF OTCC (Open Transport Configuration & Control) Project";
  contact
    "
     Project Web: <https://urldefense.com/v3/__https://wiki.opennetworking.org/display/OTCC/TAPI__;!!OSsGDw!d_dJlNtYLmD585It0DKukzB2TS5KZqBZQ-pdI1D-6c6c5hRDotd6G39KDEbL$ >
     Project List: <mailto:transport-api@opennetworking.org>
     Editor: Karthik Sethuraman <mailto:karthik.sethuraman@necam.com>
     Andrea Mazzini <mailto:andrea.mazzini@nokia.com>
     Arturo Mayoral <mailto:arturo.mayoral@telefonica.com>
     Nigel Davis <mailto:ndavis@ciena.com>";
  description
    "
     This module contains TAPI OAM Model definitions.
     Source: TapiOam.uml
     - The TAPI YANG models included in this TAPI release are a *normative* part of the TAPI SDK.
     - The YANG specifications have been generated from the corresponding UML model using the [ONF EAGLE UML2YANG mapping tool]
     <https://urldefense.com/v3/__https://github.com/OpenNetworkingFoundation/EagleUmlYang__;!!OSsGDw!d_dJlNtYLmD585It0DKukzB2TS5KZqBZQ-pdI1D-6c6c5hRDotd6G4QHf0bG$ >
     and further edited manually to comply with the [ONF IISOMI UML2YANG mapping guidelines]
     <https://urldefense.com/v3/__https://wiki.opennetworking.org/display/OIMT/UML*-*YANG*Guidelines__;Kysr!!OSsGDw!d_dJlNtYLmD585It0DKukzB2TS5KZqBZQ-pdI1D-6c6c5hRDotd6G8IIivez$ >
     - Status of YANG model artifacts can be determined by referring to the corresponding UML artifacts.
     As described in the UML models, some artifacts are considered *experimental*, and thus the corresponding YANG artifacts.
     - The ONF TAPI release process does not guarantee backward compatibility of YANG models across major versions of TAPI releases.
     The YANG model backward compatibility criteria are outlined in section 11 of <https://urldefense.com/v3/__https://tools.ietf.org/html/rfc7950__;!!OSsGDw!d_dJlNtYLmD585It0DKukzB2TS5KZqBZQ-pdI1D-6c6c5hRDotd6G3bKxRf2$ >.
     YANG models included in this release may not be backward compatible with previous TAPI releases.
     Copyright (c) 2018 Open Networking Foundation (ONF). All rights reserved.
     License: This module is distributed under the Apache License 2.0";

  revision 2020-04-23 {
    description
      "ONF Transport API version 2.1.3.
       Changes included in this TAPI release (v2.1.3) are listed in
       <https://urldefense.com/v3/__https://github.com/OpenNetworkingFoundation/TAPI/blob/develop_v2_1/CHANGE_LOG/change-log.2.1.3.md__;!!OSsGDw!d_dJlNtYLmD585It0DKukzB2TS5KZqBZQ-pdI1D-6c6c5hRDotd6G7tqhxFK$ >";
    reference
      "ONF-TR-527, ONF-TR-512, ONF-TR-531, RFC 7950, RFC 6087 and ONF TAPI UML model
       <https://urldefense.com/v3/__https://github.com/OpenNetworkingFoundation/TAPI/tree/v2.1.0/UML__;!!OSsGDw!d_dJlNtYLmD585It0DKukzB2TS5KZqBZQ-pdI1D-6c6c5hRDotd6G7KeAhLL$ >";
  }
  revision 2019-07-16 {
    description
      "ONF Transport API version 2.1.2.
       Changes included in this TAPI release (v2.1.2) are listed in
       <https://urldefense.com/v3/__https://github.com/OpenNetworkingFoundation/TAPI/blob/develop_v2_1/CHANGE_LOG/change-log.2.1.2.md__;!!OSsGDw!d_dJlNtYLmD585It0DKukzB2TS5KZqBZQ-pdI1D-6c6c5hRDotd6G7eDS6-t$ >";
    reference
      "ONF-TR-527, ONF-TR-512, ONF-TR-531, RFC 7950, RFC 6087 and ONF TAPI UML model
       <https://urldefense.com/v3/__https://github.com/OpenNetworkingFoundation/TAPI/tree/v2.1.0/UML__;!!OSsGDw!d_dJlNtYLmD585It0DKukzB2TS5KZqBZQ-pdI1D-6c6c5hRDotd6G7KeAhLL$ >";
  }
  revision 2018-12-10 {
    description
      "ONF Transport API version 2.1.1.
       Changes included in this TAPI release (v2.1.1) are listed in
       <https://urldefense.com/v3/__https://github.com/OpenNetworkingFoundation/TAPI/blob/develop/CHANGE_LOG/change-log.2.1.1.md__;!!OSsGDw!d_dJlNtYLmD585It0DKukzB2TS5KZqBZQ-pdI1D-6c6c5hRDotd6G1ftwU5J$ >";
    reference
      "ONF-TR-527, ONF-TR-512, ONF-TR-531, RFC 7950, RFC 6087 and ONF TAPI UML model
       <https://urldefense.com/v3/__https://github.com/OpenNetworkingFoundation/TAPI/tree/v2.1.0/UML__;!!OSsGDw!d_dJlNtYLmD585It0DKukzB2TS5KZqBZQ-pdI1D-6c6c5hRDotd6G7KeAhLL$ >";
  }
  revision 2018-10-16 {
    description
      "ONF Transport API version 2.1.0.
       Changes included in this TAPI release (v2.1.0) are listed in
       <https://urldefense.com/v3/__https://github.com/OpenNetworkingFoundation/TAPI/blob/develop/CHANGE_LOG/change-log.2.1.0.md__;!!OSsGDw!d_dJlNtYLmD585It0DKukzB2TS5KZqBZQ-pdI1D-6c6c5hRDotd6G-5JStw4$ >";
    reference
      "ONF-TR-527, ONF-TR-512, ONF-TR-531, RFC 7950, RFC 6087 and ONF TAPI UML model
       <https://urldefense.com/v3/__https://github.com/OpenNetworkingFoundation/TAPI/tree/v2.1.0/UML__;!!OSsGDw!d_dJlNtYLmD585It0DKukzB2TS5KZqBZQ-pdI1D-6c6c5hRDotd6G7KeAhLL$ >";
  }
  revision 2018-03-07 {
    description
      "ONF Transport API version 2.0.2
       This YANG module has been generated from the TAPI UML Model using the IISOMI-Eagle xmi2yang mapping tool.
       Changes in this revision: <https://urldefense.com/v3/__https://github.com/OpenNetworkingFoundation/TAPI/blob/develop/CHANGE_LOG/change-log.2.0.2.md__;!!OSsGDw!d_dJlNtYLmD585It0DKukzB2TS5KZqBZQ-pdI1D-6c6c5hRDotd6G1Yf4AAN$ >";
    reference
      "ONF-TR-527, ONF-TR-512, ONF-TR-531, RFC 6020, RFC 6087 and ONF TAPI UML model
       <https://urldefense.com/v3/__https://github.com/OpenNetworkingFoundation/TAPI/tree/v2.0.2/UML__;!!OSsGDw!d_dJlNtYLmD585It0DKukzB2TS5KZqBZQ-pdI1D-6c6c5hRDotd6G27-pJK_$ >";
  }
  revision 2018-02-16 {
    description
      "ONF Transport API version 2.0.1
       This YANG module has been generated from the TAPI UML Model using the IISOMI-Eagle xmi2yang mapping tool.
       Changes in this revision: <https://urldefense.com/v3/__https://github.com/OpenNetworkingFoundation/TAPI/blob/develop/CHANGE_LOG/change-log.2.0.1.md__;!!OSsGDw!d_dJlNtYLmD585It0DKukzB2TS5KZqBZQ-pdI1D-6c6c5hRDotd6G8RnGvXg$ >";
    reference
      "ONF-TR-527, ONF-TR-512, ONF-TR-531, RFC 6020, RFC 6087 and ONF TAPI UML model
       <https://urldefense.com/v3/__https://github.com/OpenNetworkingFoundation/TAPI/tree/v2.0.1/UML__;!!OSsGDw!d_dJlNtYLmD585It0DKukzB2TS5KZqBZQ-pdI1D-6c6c5hRDotd6Gy6YoeAv$ >";
  }
  revision 2018-01-02 {
    description
      "ONF Transport API version 2.0.0
       This YANG module has been generated from the TAPI UML Model using the IISOMI-Eagle xmi2yang mapping tool.
       Changes in this revision: <https://urldefense.com/v3/__https://github.com/OpenNetworkingFoundation/TAPI/blob/develop/CHANGE_LOG/change-log.2.0.0.md__;!!OSsGDw!d_dJlNtYLmD585It0DKukzB2TS5KZqBZQ-pdI1D-6c6c5hRDotd6GyqYDgG_$ >";
    reference
      "ONF-TR-527, ONF-TR-512, ONF-TR-531, RFC 6020, RFC 6087 and ONF TAPI UML model
       <https://urldefense.com/v3/__https://github.com/OpenNetworkingFoundation/TAPI/tree/v2.0.0/UML__;!!OSsGDw!d_dJlNtYLmD585It0DKukzB2TS5KZqBZQ-pdI1D-6c6c5hRDotd6G1V9Thk9$ >";
  }

  typedef ncs_template_oam-job-type {
    type string;
    description
      "none";
  }

  typedef ncs_rpc_notif_oam-job-type {
    type identityref {
      base OAM_JOB_TYPE;
    }
    description
      "none";
  }

  typedef live_ncs_oam-job-type {
    type identityref {
      base OAM_JOB_TYPE;
    }
    description
      "none";
  }

  typedef oam-job-type {
    type identityref {
      base OAM_JOB_TYPE;
    }
    description
      "none";
  }

  grouping ncs_template_oam-service-ref {
    leaf oam-service-uuid {
      type string;
      description
        "none";
    }
    description
      "none";
  }

  grouping ncs_template_oam-service-end-point-ref {
    uses ncs_template_oam-service-ref;
    leaf oam-service-end-point-local-id {
      type string;
      description
        "none";
    }
    description
      "none";
  }

  grouping ncs_template_meg-ref {
    leaf meg-uuid {
      type string;
      description
        "none";
    }
    description
      "none";
  }

  grouping ncs_template_maintenance-entity-ref {
    uses ncs_template_meg-ref;
    leaf maintenance-entity-local-id {
      type string;
      description
        "none";
    }
    description
      "none";
  }

  grouping ncs_template_mep-ref {
    uses ncs_template_meg-ref;
    leaf mep-local-id {
      type string;
      description
        "none";
    }
    description
      "none";
  }

  grouping ncs_template_mip-ref {
    uses ncs_template_meg-ref;
    leaf mip-local-id {
      type string;
      description
        "none";
    }
    description
      "none";
  }

  grouping ncs_template_oam-job-ref {
    leaf oam-job-uuid {
      type string;
      description
        "none";
    }
    description
      "none";
  }

  grouping ncs_template_pm-current-data-ref {
    uses ncs_template_oam-job-ref;
    leaf pm-current-data-local-id {
      type string;
      description
        "none";
    }
    description
      "none";
  }

  grouping ncs_template_pm-history-data-ref {
    uses ncs_template_pm-current-data-ref;
    leaf pm-history-data-local-id {
      type string;
      description
        "none";
    }
    description
      "none";
  }

  grouping ncs_template_oam-profile-ref {
    leaf oam-profile-uuid {
      type string;
      description
        "none";
    }
    description
      "none";
  }

  grouping ncs_template_pm-threshold-data-ref {
    uses ncs_template_oam-profile-ref;
    leaf pm-threshold-data-local-id {
      type string;
      description
        "none";
    }
    description
      "none";
  }

  grouping ncs_template_pm-bin-data-ref {
    uses ncs_template_oam-profile-ref;
    leaf pm-bin-data-local-id {
      type string;
      description
        "none";
    }
    description
      "none";
  }

  grouping ncs_template_mep {
    // NCS drop config false leaf 'layer-protocol-name'
    // NCS drop config false leaf direction
    // NCS drop config false leaf 'mep-identifier'
    // NCS drop config false leaf-list 'peer-mep-identifier'
    uses tapi-common:ncs_template_local-class;
    uses tapi-common:ncs_template_operational-state-pac;
    description
      "none";
  }

  grouping ncs_template_oam-job {
    list oam-service-end-point {
      // NCS patched for predictable order
      ordered-by user;
      uses ncs_template_oam-service-end-point-ref;
      key "oam-service-uuid oam-service-end-point-local-id";
      // NCS drop min-elements statement
      description
        "none";
    }
    container oam-profile {
      uses ncs_template_oam-profile-ref;
      description
        "none";
    }
    // NCS drop config false list 'pm-current-data'
    leaf oam-job-type {
      type ncs_template_oam-job-type;
      description
        "none";
    }
    container schedule {
      uses tapi-common:ncs_template_time-range;
      description
        "none";
    }
    // NCS drop config false leaf 'creation-time'
    uses tapi-common:ncs_template_global-class;
    uses tapi-common:ncs_template_admin-state-pac;
    description
      "none";
  }

  grouping ncs_template_meg {
    // NCS drop config false list mep
    // NCS drop config false list mip
    // NCS drop config false leaf 'layer-protocol-name'
    // NCS drop config false leaf direction
    // NCS drop config false leaf 'meg-level'
    // NCS drop config false leaf 'meg-identifier'
    uses tapi-common:ncs_template_resource-spec;
    uses tapi-common:ncs_template_operational-state-pac;
    description
      "none";
  }

  grouping ncs_template_mip {
    // NCS drop config false leaf 'layer-protocol-name'
    uses tapi-common:ncs_template_local-class;
    description
      "none";
  }

  grouping ncs_template_oam-service {
    list end-point {
      // NCS patched for predictable order
      ordered-by user;
      key "local-id";
      // NCS drop min-elements statement
      uses ncs_template_oam-service-end-point;
      description
        "none";
    }
    // NCS drop config false container meg
    container oam-profile {
      uses ncs_template_oam-profile-ref;
      description
        "none";
    }
    uses tapi-common:ncs_template_service-spec;
    uses tapi-common:ncs_template_admin-state-pac;
    uses ncs_template_oam-constraint;
    description
      "none";
  }

  grouping ncs_template_oam-context {
    list oam-service {
      // NCS patched for predictable order
      ordered-by user;
      key "uuid";
      uses ncs_template_oam-service;
      description
        "none";
    }
    // NCS drop config false list meg
    list oam-job {
      // NCS patched for predictable order
      ordered-by user;
      key "uuid";
      uses ncs_template_oam-job;
      description
        "none";
    }
    list oam-profile {
      // NCS patched for predictable order
      ordered-by user;
      key "uuid";
      uses ncs_template_oam-profile;
      description
        "none";
    }
    description
      "none";
  }

  grouping ncs_template_oam-service-end-point {
    container service-interface-point {
      uses tapi-common:ncs_template_service-interface-point-ref;
      description
        "none";
    }
    container connectivity-service-end-point {
      uses tapi-connectivity:ncs_template_connectivity-service-end-point-ref;
      description
        "none";
    }
    // NCS drop config false container mep
    // NCS drop config false container mip
    leaf layer-protocol-name {
      type tapi-common:ncs_template_layer-protocol-name;
      description
        "none";
    }
    leaf direction {
      type tapi-common:ncs_template_port-direction;
      description
        "none";
    }
    leaf mep-identifier {
      type string;
      description
        "This attribute contains the identifier of the MEP.
         This attribute is empty in case the OSEP relates to the provisioing of an MIP.
        ";
    }
    leaf-list peer-mep-identifier {
      // NCS patched for predictable order
      ordered-by user;
      type string;
      description
        "This attribute models the MI_PeerMEP_ID[i] defined in G.8021 and configured as specified in G.8051. It provides the identifiers of the MEPs which are peer to the subject MEP.
         This attribute is not specified in case the OSEP relates to the provisioing of an MIP.
         In case of P2P, there is only one peer";
    }
    uses tapi-common:ncs_template_local-class;
    uses tapi-common:ncs_template_admin-state-pac;
    description
      "none";
  }

  grouping ncs_template_mep-mip-list {
    list mip {
      // NCS patched for predictable order
      ordered-by user;
      uses ncs_template_mip-ref;
      key "meg-uuid mip-local-id";
      description
        "none";
    }
    list mep {
      // NCS patched for predictable order
      ordered-by user;
      uses ncs_template_mep-ref;
      key "meg-uuid mep-local-id";
      description
        "none";
    }
    description
      "none";
  }

  grouping ncs_template_oam-constraint {
    leaf layer-protocol-name {
      type tapi-common:ncs_template_layer-protocol-name;
      description
        "none";
    }
    leaf direction {
      type tapi-common:ncs_template_forwarding-direction;
      description
        "none";
    }
    leaf meg-level {
      type string;
      description
        "none";
    }
    description
      "none";
  }

  grouping ncs_template_pm-current-data {
    // NCS drop config false list 'pm-history-data'
    container granularity-period {
      uses tapi-common:ncs_template_time-period;
      description
        "none";
    }
    // NCS drop config false leaf timestamp
    container elapsed-time {
      uses tapi-common:ncs_template_time-interval;
      description
        "none";
    }
    leaf suspect-interval-flag {
      type string;
      description
        "This attribute is used to indicate that the performance data for the current period may not be reliable. Some reasons for this to occur are:
         - Suspect data were detected by the actual resource doing data collection.
         - Transition of the administrativeState attribute to/from the 'lock' state.
         - Transition of the operationalState to/from the 'disabled' state.
         - Scheduler setting that inhibits the collection function.
         - The performance counters were reset during the interval.
         - The currentData (or subclass) object instance was created during the monitoring period.";
    }
    uses tapi-common:ncs_template_local-class;
    description
      "none";
  }

  grouping ncs_template_pm-history-data {
    container granularity-period {
      uses tapi-common:ncs_template_time-period;
      description
        "none";
    }
    leaf period-end-time {
      type tapi-common:ncs_template_date-and-time;
      description
        "none";
    }
    // NCS drop config false leaf 'suspect-interval-flag'
    uses tapi-common:ncs_template_local-class;
    description
      "none";
  }

  grouping ncs_template_oam-profile {
    list pm-threshold-data {
      // NCS patched for predictable order
      ordered-by user;
      key "local-id";
      // NCS drop min-elements statement
      uses ncs_template_pm-threshold-data;
      description
        "none";
    }
    list pm-bin-data {
      // NCS patched for predictable order
      ordered-by user;
      key "local-id";
      // NCS drop min-elements statement
      uses ncs_template_pm-bin-data;
      description
        "none";
    }
    uses tapi-common:ncs_template_global-class;
    description
      "none";
  }

  grouping ncs_template_pm-threshold-data {
    container granularity-period {
      uses tapi-common:ncs_template_time-period;
      description
        "none";
    }
    leaf is-transient {
      type string;
      description
        "none";
    }
    uses tapi-common:ncs_template_local-class;
    description
      "none";
  }

  grouping ncs_template_pm-bin-data {
    container granularity-period {
      uses tapi-common:ncs_template_time-period;
      description
        "none";
    }
    uses tapi-common:ncs_template_local-class;
    description
      "none";
  }

  grouping ncs_rpc_notif_oam-service-ref {
    leaf oam-service-uuid {
      type string;
      description
        "none";
    }
    description
      "none";
  }

  grouping ncs_rpc_notif_oam-service-end-point-ref {
    uses ncs_rpc_notif_oam-service-ref;
    leaf oam-service-end-point-local-id {
      type string;
      description
        "none";
    }
    description
      "none";
  }

  grouping ncs_rpc_notif_meg-ref {
    leaf meg-uuid {
      type string;
      description
        "none";
    }
    description
      "none";
  }

  grouping ncs_rpc_notif_maintenance-entity-ref {
    uses ncs_rpc_notif_meg-ref;
    leaf maintenance-entity-local-id {
      type string;
      description
        "none";
    }
    description
      "none";
  }

  grouping ncs_rpc_notif_mep-ref {
    uses ncs_rpc_notif_meg-ref;
    leaf mep-local-id {
      type string;
      description
        "none";
    }
    description
      "none";
  }

  grouping ncs_rpc_notif_mip-ref {
    uses ncs_rpc_notif_meg-ref;
    leaf mip-local-id {
      type string;
      description
        "none";
    }
    description
      "none";
  }

  grouping ncs_rpc_notif_oam-job-ref {
    leaf oam-job-uuid {
      type string;
      description
        "none";
    }
    description
      "none";
  }

  grouping ncs_rpc_notif_pm-current-data-ref {
    uses ncs_rpc_notif_oam-job-ref;
    leaf pm-current-data-local-id {
      type string;
      description
        "none";
    }
    description
      "none";
  }

  grouping ncs_rpc_notif_pm-history-data-ref {
    uses ncs_rpc_notif_pm-current-data-ref;
    leaf pm-history-data-local-id {
      type string;
      description
        "none";
    }
    description
      "none";
  }

  grouping ncs_rpc_notif_oam-profile-ref {
    leaf oam-profile-uuid {
      type string;
      description
        "none";
    }
    description
      "none";
  }

  grouping ncs_rpc_notif_pm-threshold-data-ref {
    uses ncs_rpc_notif_oam-profile-ref;
    leaf pm-threshold-data-local-id {
      type string;
      description
        "none";
    }
    description
      "none";
  }

  grouping ncs_rpc_notif_pm-bin-data-ref {
    uses ncs_rpc_notif_oam-profile-ref;
    leaf pm-bin-data-local-id {
      type string;
      description
        "none";
    }
    description
      "none";
  }

  grouping ncs_rpc_notif_mep {
    leaf layer-protocol-name {
      type tapi-common:ncs_rpc_notif_layer-protocol-name;
      config false;
      description
        "none";
    }
    leaf direction {
      type tapi-common:ncs_rpc_notif_termination-direction;
      config false;
      description
        "none";
    }
    leaf mep-identifier {
      type string;
      config false;
      description
        "none";
    }
    leaf-list peer-mep-identifier {
      type string;
      config false;
      min-elements 1;
      description
        "none";
    }
    uses tapi-common:ncs_rpc_notif_local-class;
    uses tapi-common:ncs_rpc_notif_operational-state-pac;
    description
      "none";
  }

  grouping ncs_rpc_notif_oam-job {
    list oam-service-end-point {
      uses ncs_rpc_notif_oam-service-end-point-ref;
      key "oam-service-uuid oam-service-end-point-local-id";
      min-elements 1;
      description
        "none";
    }
    container oam-profile {
      uses ncs_rpc_notif_oam-profile-ref;
      description
        "none";
    }
    list pm-current-data {
      key "local-id";
      config false;
      uses ncs_rpc_notif_pm-current-data;
      description
        "Granularity period of the CurrentData identifies the specific CurrentData instance in the scope of this OamJob.
         For example, typically at least
         one 15min and
         one 24hr;
         optionally one additional configurable (< 15min)";
    }
    leaf oam-job-type {
      type ncs_rpc_notif_oam-job-type;
      description
        "none";
    }
    container schedule {
      uses tapi-common:ncs_rpc_notif_time-range;
      description
        "none";
    }
    leaf creation-time {
      type tapi-common:ncs_rpc_notif_date-and-time;
      config false;
      description
        "none";
    }
    uses tapi-common:ncs_rpc_notif_global-class;
    uses tapi-common:ncs_rpc_notif_admin-state-pac;
    description
      "none";
  }

  grouping ncs_rpc_notif_meg {
    list mep {
      key "local-id";
      config false;
      uses ncs_rpc_notif_mep;
      description
        "1. ME may have 0 MEPs (case of transit domains where at least 1 MIP is present)
         2. ME may have 1 MEP (case of edge domaind, where the peer MEP is ouside the managed domain)
         3. ME may have 2 MEPs";
    }
    list mip {
      key "local-id";
      config false;
      uses ncs_rpc_notif_mip;
      description
        "ME may 0, 1, or more MIPs";
    }
    leaf layer-protocol-name {
      type tapi-common:ncs_rpc_notif_layer-protocol-name;
      config false;
      description
        "none";
    }
    leaf direction {
      type tapi-common:ncs_rpc_notif_forwarding-direction;
      config false;
      description
        "none";
    }
    leaf meg-level {
      type uint64;
      config false;
      description
        "none";
    }
    leaf meg-identifier {
      type string;
      config false;
      description
        "none";
    }
    uses tapi-common:ncs_rpc_notif_resource-spec;
    uses tapi-common:ncs_rpc_notif_operational-state-pac;
    description
      "none";
  }

  grouping ncs_rpc_notif_mip {
    leaf layer-protocol-name {
      type tapi-common:ncs_rpc_notif_layer-protocol-name;
      config false;
      description
        "none";
    }
    uses tapi-common:ncs_rpc_notif_local-class;
    description
      "none";
  }

  grouping ncs_rpc_notif_oam-service {
    list end-point {
      key "local-id";
      min-elements 2;
      uses ncs_rpc_notif_oam-service-end-point;
      description
        "none";
    }
    container meg {
      uses ncs_rpc_notif_meg-ref;
      config false;
      description
        "none";
    }
    container oam-profile {
      uses ncs_rpc_notif_oam-profile-ref;
      description
        "none";
    }
    uses tapi-common:ncs_rpc_notif_service-spec;
    uses tapi-common:ncs_rpc_notif_admin-state-pac;
    uses ncs_rpc_notif_oam-constraint;
    description
      "none";
  }

  grouping ncs_rpc_notif_oam-context {
    list oam-service {
      key "uuid";
      uses ncs_rpc_notif_oam-service;
      description
        "none";
    }
    list meg {
      key "uuid";
      config false;
      uses ncs_rpc_notif_meg;
      description
        "none";
    }
    list oam-job {
      key "uuid";
      uses ncs_rpc_notif_oam-job;
      description
        "none";
    }
    list oam-profile {
      key "uuid";
      uses ncs_rpc_notif_oam-profile;
      description
        "none";
    }
    description
      "none";
  }

  grouping ncs_rpc_notif_oam-service-end-point {
    container service-interface-point {
      uses tapi-common:ncs_rpc_notif_service-interface-point-ref;
      description
        "none";
    }
    container connectivity-service-end-point {
      uses tapi-connectivity:ncs_rpc_notif_connectivity-service-end-point-ref;
      description
        "none";
    }
    container mep {
      uses ncs_rpc_notif_mep-ref;
      config false;
      description
        "none";
    }
    container mip {
      uses ncs_rpc_notif_mip-ref;
      config false;
      description
        "none";
    }
    leaf layer-protocol-name {
      type tapi-common:ncs_rpc_notif_layer-protocol-name;
      description
        "none";
    }
    leaf direction {
      type tapi-common:ncs_rpc_notif_port-direction;
      description
        "none";
    }
    leaf mep-identifier {
      type string;
      description
        "This attribute contains the identifier of the MEP.
         This attribute is empty in case the OSEP relates to the provisioing of an MIP.
        ";
    }
    leaf-list peer-mep-identifier {
      type string;
      description
        "This attribute models the MI_PeerMEP_ID[i] defined in G.8021 and configured as specified in G.8051. It provides the identifiers of the MEPs which are peer to the subject MEP.
         This attribute is not specified in case the OSEP relates to the provisioing of an MIP.
         In case of P2P, there is only one peer";
    }
    uses tapi-common:ncs_rpc_notif_local-class;
    uses tapi-common:ncs_rpc_notif_admin-state-pac;
    description
      "none";
  }

  grouping ncs_rpc_notif_mep-mip-list {
    list mip {
      uses ncs_rpc_notif_mip-ref;
      key "meg-uuid mip-local-id";
      description
        "none";
    }
    list mep {
      uses ncs_rpc_notif_mep-ref;
      key "meg-uuid mep-local-id";
      description
        "none";
    }
    description
      "none";
  }

  grouping ncs_rpc_notif_oam-constraint {
    leaf layer-protocol-name {
      type tapi-common:ncs_rpc_notif_layer-protocol-name;
      description
        "none";
    }
    leaf direction {
      type tapi-common:ncs_rpc_notif_forwarding-direction;
      description
        "none";
    }
    leaf meg-level {
      type uint64;
      description
        "none";
    }
    description
      "none";
  }

  grouping ncs_rpc_notif_pm-current-data {
    list pm-history-data {
      key "local-id";
      config false;
      uses ncs_rpc_notif_pm-history-data;
      description
        "in case of 24hr Current Data, at least 1 History Data.
         In case of 15min Current Data, at least 16 History Data.
         In case of <15min, the number of History Data shall be able to cover a span of 4 hours.";
    }
    container granularity-period {
      uses tapi-common:ncs_rpc_notif_time-period;
      description
        "none";
    }
    leaf timestamp {
      type tapi-common:ncs_rpc_notif_date-and-time;
      config false;
      description
        "This attribute indicates the start of the current monitoring interval.
         The value is bound to the quarter of an hour in case of a 15 minute interval and bound to the hour in case of a 24 hour interval.";
    }
    container elapsed-time {
      uses tapi-common:ncs_rpc_notif_time-interval;
      description
        "none";
    }
    leaf suspect-interval-flag {
      type boolean;
      description
        "This attribute is used to indicate that the performance data for the current period may not be reliable. Some reasons for this to occur are:
         - Suspect data were detected by the actual resource doing data collection.
         - Transition of the administrativeState attribute to/from the 'lock' state.
         - Transition of the operationalState to/from the 'disabled' state.
         - Scheduler setting that inhibits the collection function.
         - The performance counters were reset during the interval.
         - The currentData (or subclass) object instance was created during the monitoring period.";
    }
    uses tapi-common:ncs_rpc_notif_local-class;
    description
      "none";
  }

  grouping ncs_rpc_notif_pm-history-data {
    container granularity-period {
      uses tapi-common:ncs_rpc_notif_time-period;
      description
        "none";
    }
    leaf period-end-time {
      type tapi-common:ncs_rpc_notif_date-and-time;
      description
        "none";
    }
    leaf suspect-interval-flag {
      type boolean;
      config false;
      description
        "This attribute indicates that the performance data may not be reliable.";
    }
    uses tapi-common:ncs_rpc_notif_local-class;
    description
      "none";
  }

  grouping ncs_rpc_notif_oam-profile {
    list pm-threshold-data {
      key "local-id";
      min-elements 1;
      uses ncs_rpc_notif_pm-threshold-data;
      description
        "none";
    }
    list pm-bin-data {
      key "local-id";
      min-elements 1;
      uses ncs_rpc_notif_pm-bin-data;
      description
        "none";
    }
    uses tapi-common:ncs_rpc_notif_global-class;
    description
      "none";
  }

  grouping ncs_rpc_notif_pm-threshold-data {
    container granularity-period {
      uses tapi-common:ncs_rpc_notif_time-period;
      description
        "none";
    }
    leaf is-transient {
      type boolean;
      description
        "none";
    }
    uses tapi-common:ncs_rpc_notif_local-class;
    description
      "none";
  }

  grouping ncs_rpc_notif_pm-bin-data {
    container granularity-period {
      uses tapi-common:ncs_rpc_notif_time-period;
      description
        "none";
    }
    uses tapi-common:ncs_rpc_notif_local-class;
    description
      "none";
  }

  grouping live_ncs_oam-service-ref {
    leaf oam-service-uuid {
      type leafref {
        path "/ncs:devices/ncs:device/ncs:live-status/tapi-common:context/tapi-oam:oam-context/tapi-oam:oam-service/tapi-oam:uuid" {
          tailf:xpath-root 3;
        }
      }
      description
        "none";
    }
    description
      "none";
  }

  grouping live_ncs_oam-service-end-point-ref {
    uses live_ncs_oam-service-ref;
    leaf oam-service-end-point-local-id {
      type leafref {
        path "/ncs:devices/ncs:device/ncs:live-status/tapi-common:context/tapi-oam:oam-context/tapi-oam:oam-service/tapi-oam:end-point/tapi-oam:local-id" {
          tailf:xpath-root 3;
        }
      }
      description
        "none";
    }
    description
      "none";
  }

  grouping live_ncs_meg-ref {
    leaf meg-uuid {
      type leafref {
        path "/ncs:devices/ncs:device/ncs:live-status/tapi-common:context/tapi-oam:oam-context/tapi-oam:meg/tapi-oam:uuid" {
          tailf:xpath-root 3;
        }
      }
      description
        "none";
    }
    description
      "none";
  }

  grouping live_ncs_maintenance-entity-ref {
    uses live_ncs_meg-ref;
    leaf maintenance-entity-local-id {
      type leafref {
        path "/ncs:devices/ncs:device/ncs:live-status/tapi-common:context/tapi-oam:oam-context/tapi-oam:meg/tapi-oam:me/tapi-oam:local-id" {
          tailf:xpath-root 3;
        }
      }
      description
        "none";
    }
    description
      "none";
  }

  grouping live_ncs_mep-ref {
    uses live_ncs_meg-ref;
    leaf mep-local-id {
      type leafref {
        path "/ncs:devices/ncs:device/ncs:live-status/tapi-common:context/tapi-oam:oam-context/tapi-oam:meg/tapi-oam:mep/tapi-oam:local-id" {
          tailf:xpath-root 3;
        }
      }
      description
        "none";
    }
    description
      "none";
  }

  grouping live_ncs_mip-ref {
    uses live_ncs_meg-ref;
    leaf mip-local-id {
      type leafref {
        path "/ncs:devices/ncs:device/ncs:live-status/tapi-common:context/tapi-oam:oam-context/tapi-oam:meg/tapi-oam:mip/tapi-oam:local-id" {
          tailf:xpath-root 3;
        }
      }
      description
        "none";
    }
    description
      "none";
  }

  grouping live_ncs_oam-job-ref {
    leaf oam-job-uuid {
      type leafref {
        path "/ncs:devices/ncs:device/ncs:live-status/tapi-common:context/tapi-oam:oam-context/tapi-oam:oam-job/tapi-oam:uuid" {
          tailf:xpath-root 3;
        }
      }
      description
        "none";
    }
    description
      "none";
  }

  grouping live_ncs_pm-current-data-ref {
    uses live_ncs_oam-job-ref;
    leaf pm-current-data-local-id {
      type leafref {
        path "/ncs:devices/ncs:device/ncs:live-status/tapi-common:context/tapi-oam:oam-context/tapi-oam:oam-job/tapi-oam:pm-current-data/tapi-oam:local-id" {
          tailf:xpath-root 3;
        }
      }
      description
        "none";
    }
    description
      "none";
  }

  grouping live_ncs_pm-history-data-ref {
    uses live_ncs_pm-current-data-ref;
    leaf pm-history-data-local-id {
      type leafref {
        path "/ncs:devices/ncs:device/ncs:live-status/tapi-common:context/tapi-oam:oam-context/tapi-oam:oam-job/tapi-oam:pm-current-data/tapi-oam:pm-history-data/tapi-oam:local-id" {
          tailf:xpath-root 3;
        }
      }
      description
        "none";
    }
    description
      "none";
  }

  grouping live_ncs_oam-profile-ref {
    leaf oam-profile-uuid {
      type leafref {
        path "/ncs:devices/ncs:device/ncs:live-status/tapi-common:context/tapi-oam:oam-context/tapi-oam:oam-profile/tapi-oam:uuid" {
          tailf:xpath-root 3;
        }
      }
      description
        "none";
    }
    description
      "none";
  }

  grouping live_ncs_pm-threshold-data-ref {
    uses live_ncs_oam-profile-ref;
    leaf pm-threshold-data-local-id {
      type leafref {
        path "/ncs:devices/ncs:device/ncs:live-status/tapi-common:context/tapi-oam:oam-context/tapi-oam:oam-profile/tapi-oam:pm-threshold-data/tapi-oam:local-id" {
          tailf:xpath-root 3;
        }
      }
      description
        "none";
    }
    description
      "none";
  }

  grouping live_ncs_pm-bin-data-ref {
    uses live_ncs_oam-profile-ref;
    leaf pm-bin-data-local-id {
      type leafref {
        path "/ncs:devices/ncs:device/ncs:live-status/tapi-common:context/tapi-oam:oam-context/tapi-oam:oam-profile/tapi-oam:pm-bin-data/tapi-oam:local-id" {
          tailf:xpath-root 3;
        }
      }
      description
        "none";
    }
    description
      "none";
  }

  grouping live_ncs_mep {
    leaf layer-protocol-name {
      type tapi-common:live_ncs_layer-protocol-name;
      description
        "none";
    }
    leaf direction {
      type tapi-common:live_ncs_termination-direction;
      description
        "none";
    }
    leaf mep-identifier {
      type string;
      description
        "none";
    }
    leaf-list peer-mep-identifier {
      type string;
      // NCS drop min-elements statement
      description
        "none";
    }
    uses tapi-common:live_ncs_local-class;
    uses tapi-common:live_ncs_operational-state-pac;
    description
      "none";
  }

  grouping live_ncs_oam-job {
    list oam-service-end-point {
      uses live_ncs_oam-service-end-point-ref;
      key "oam-service-uuid oam-service-end-point-local-id";
      // NCS drop min-elements statement
      description
        "none";
    }
    container oam-profile {
      uses live_ncs_oam-profile-ref;
      description
        "none";
    }
    list pm-current-data {
      key "local-id";
      uses live_ncs_pm-current-data;
      description
        "Granularity period of the CurrentData identifies the specific CurrentData instance in the scope of this OamJob.
         For example, typically at least
         one 15min and
         one 24hr;
         optionally one additional configurable (< 15min)";
    }
    leaf oam-job-type {
      type live_ncs_oam-job-type;
      description
        "none";
    }
    container schedule {
      uses tapi-common:live_ncs_time-range;
      description
        "none";
    }
    leaf creation-time {
      type tapi-common:live_ncs_date-and-time;
      description
        "none";
    }
    uses tapi-common:live_ncs_global-class;
    uses tapi-common:live_ncs_admin-state-pac;
    description
      "none";
  }

  grouping live_ncs_meg {
    list mep {
      key "local-id";
      uses live_ncs_mep;
      description
        "1. ME may have 0 MEPs (case of transit domains where at least 1 MIP is present)
         2. ME may have 1 MEP (case of edge domaind, where the peer MEP is ouside the managed domain)
         3. ME may have 2 MEPs";
    }
    list mip {
      key "local-id";
      uses live_ncs_mip;
      description
        "ME may 0, 1, or more MIPs";
    }
    leaf layer-protocol-name {
      type tapi-common:live_ncs_layer-protocol-name;
      description
        "none";
    }
    leaf direction {
      type tapi-common:live_ncs_forwarding-direction;
      description
        "none";
    }
    leaf meg-level {
      type uint64;
      description
        "none";
    }
    leaf meg-identifier {
      type string;
      description
        "none";
    }
    uses tapi-common:live_ncs_resource-spec;
    uses tapi-common:live_ncs_operational-state-pac;
    description
      "none";
  }

  grouping live_ncs_mip {
    leaf layer-protocol-name {
      type tapi-common:live_ncs_layer-protocol-name;
      description
        "none";
    }
    uses tapi-common:live_ncs_local-class;
    description
      "none";
  }

  grouping live_ncs_oam-service {
    list end-point {
      key "local-id";
      // NCS drop min-elements statement
      uses live_ncs_oam-service-end-point;
      description
        "none";
    }
    container meg {
      uses live_ncs_meg-ref;
      description
        "none";
    }
    container oam-profile {
      uses live_ncs_oam-profile-ref;
      description
        "none";
    }
    uses tapi-common:live_ncs_service-spec;
    uses tapi-common:live_ncs_admin-state-pac;
    uses live_ncs_oam-constraint;
    description
      "none";
  }

  grouping live_ncs_oam-context {
    list oam-service {
      key "uuid";
      uses live_ncs_oam-service;
      description
        "none";
    }
    list meg {
      key "uuid";
      uses live_ncs_meg;
      description
        "none";
    }
    list oam-job {
      key "uuid";
      uses live_ncs_oam-job;
      description
        "none";
    }
    list oam-profile {
      key "uuid";
      uses live_ncs_oam-profile;
      description
        "none";
    }
    description
      "none";
  }

  grouping live_ncs_oam-service-end-point {
    container service-interface-point {
      uses tapi-common:live_ncs_service-interface-point-ref;
      description
        "none";
    }
    container connectivity-service-end-point {
      uses tapi-connectivity:live_ncs_connectivity-service-end-point-ref;
      description
        "none";
    }
    container mep {
      uses live_ncs_mep-ref;
      description
        "none";
    }
    container mip {
      uses live_ncs_mip-ref;
      description
        "none";
    }
    leaf layer-protocol-name {
      type tapi-common:live_ncs_layer-protocol-name;
      description
        "none";
    }
    leaf direction {
      type tapi-common:live_ncs_port-direction;
      description
        "none";
    }
    leaf mep-identifier {
      type string;
      description
        "This attribute contains the identifier of the MEP.
         This attribute is empty in case the OSEP relates to the provisioing of an MIP.
        ";
    }
    leaf-list peer-mep-identifier {
      type string;
      description
        "This attribute models the MI_PeerMEP_ID[i] defined in G.8021 and configured as specified in G.8051. It provides the identifiers of the MEPs which are peer to the subject MEP.
         This attribute is not specified in case the OSEP relates to the provisioing of an MIP.
         In case of P2P, there is only one peer";
    }
    uses tapi-common:live_ncs_local-class;
    uses tapi-common:live_ncs_admin-state-pac;
    description
      "none";
  }

  grouping live_ncs_mep-mip-list {
    list mip {
      uses live_ncs_mip-ref;
      key "meg-uuid mip-local-id";
      description
        "none";
    }
    list mep {
      uses live_ncs_mep-ref;
      key "meg-uuid mep-local-id";
      description
        "none";
    }
    description
      "none";
  }

  grouping live_ncs_oam-constraint {
    leaf layer-protocol-name {
      type tapi-common:live_ncs_layer-protocol-name;
      description
        "none";
    }
    leaf direction {
      type tapi-common:live_ncs_forwarding-direction;
      description
        "none";
    }
    leaf meg-level {
      type uint64;
      description
        "none";
    }
    description
      "none";
  }

  grouping live_ncs_pm-current-data {
    list pm-history-data {
      key "local-id";
      uses live_ncs_pm-history-data;
      description
        "in case of 24hr Current Data, at least 1 History Data.
         In case of 15min Current Data, at least 16 History Data.
         In case of <15min, the number of History Data shall be able to cover a span of 4 hours.";
    }
    container granularity-period {
      uses tapi-common:live_ncs_time-period;
      description
        "none";
    }
    leaf timestamp {
      type tapi-common:live_ncs_date-and-time;
      description
        "This attribute indicates the start of the current monitoring interval.
         The value is bound to the quarter of an hour in case of a 15 minute interval and bound to the hour in case of a 24 hour interval.";
    }
    container elapsed-time {
      uses tapi-common:live_ncs_time-interval;
      description
        "none";
    }
    leaf suspect-interval-flag {
      type boolean;
      description
        "This attribute is used to indicate that the performance data for the current period may not be reliable. Some reasons for this to occur are:
         - Suspect data were detected by the actual resource doing data collection.
         - Transition of the administrativeState attribute to/from the 'lock' state.
         - Transition of the operationalState to/from the 'disabled' state.
         - Scheduler setting that inhibits the collection function.
         - The performance counters were reset during the interval.
         - The currentData (or subclass) object instance was created during the monitoring period.";
    }
    uses tapi-common:live_ncs_local-class;
    description
      "none";
  }

  grouping live_ncs_pm-history-data {
    container granularity-period {
      uses tapi-common:live_ncs_time-period;
      description
        "none";
    }
    leaf period-end-time {
      type tapi-common:live_ncs_date-and-time;
      description
        "none";
    }
    leaf suspect-interval-flag {
      type boolean;
      description
        "This attribute indicates that the performance data may not be reliable.";
    }
    uses tapi-common:live_ncs_local-class;
    description
      "none";
  }

  grouping live_ncs_oam-profile {
    list pm-threshold-data {
      key "local-id";
      // NCS drop min-elements statement
      uses live_ncs_pm-threshold-data;
      description
        "none";
    }
    list pm-bin-data {
      key "local-id";
      // NCS drop min-elements statement
      uses live_ncs_pm-bin-data;
      description
        "none";
    }
    uses tapi-common:live_ncs_global-class;
    description
      "none";
  }

  grouping live_ncs_pm-threshold-data {
    container granularity-period {
      uses tapi-common:live_ncs_time-period;
      description
        "none";
    }
    leaf is-transient {
      type boolean;
      description
        "none";
    }
    uses tapi-common:live_ncs_local-class;
    description
      "none";
  }

  grouping live_ncs_pm-bin-data {
    container granularity-period {
      uses tapi-common:live_ncs_time-period;
      description
        "none";
    }
    uses tapi-common:live_ncs_local-class;
    description
      "none";
  }

  grouping oam-service-ref {
    leaf oam-service-uuid {
      type leafref {
        path "/ncs:devices/ncs:device/ncs:config/tapi-common:context/tapi-oam:oam-context/tapi-oam:oam-service/tapi-oam:uuid" {
          tailf:xpath-root 3;
        }
      }
      description
        "none";
    }
    description
      "none";
  }

  grouping oam-service-end-point-ref {
    uses oam-service-ref;
    leaf oam-service-end-point-local-id {
      type leafref {
        path "/ncs:devices/ncs:device/ncs:config/tapi-common:context/tapi-oam:oam-context/tapi-oam:oam-service/tapi-oam:end-point/tapi-oam:local-id" {
          tailf:xpath-root 3;
        }
      }
      description
        "none";
    }
    description
      "none";
  }

  grouping meg-ref {
    leaf meg-uuid {
      type leafref {
        path "/ncs:devices/ncs:device/ncs:live-status/tapi-common:context/tapi-oam:oam-context/tapi-oam:meg/tapi-oam:uuid" {
          tailf:xpath-root 2;
        }
      }
      description
        "none";
    }
    description
      "none";
  }

  grouping maintenance-entity-ref {
    uses meg-ref;
    leaf maintenance-entity-local-id {
      type string;
      description
        "none";
    }
    description
      "none";
  }

  grouping mep-ref {
    uses meg-ref;
    leaf mep-local-id {
      type leafref {
        path "/ncs:devices/ncs:device/ncs:live-status/tapi-common:context/tapi-oam:oam-context/tapi-oam:meg/tapi-oam:mep/tapi-oam:local-id" {
          tailf:xpath-root 2;
        }
      }
      description
        "none";
    }
    description
      "none";
  }

  grouping mip-ref {
    uses meg-ref;
    leaf mip-local-id {
      type leafref {
        path "/ncs:devices/ncs:device/ncs:live-status/tapi-common:context/tapi-oam:oam-context/tapi-oam:meg/tapi-oam:mip/tapi-oam:local-id" {
          tailf:xpath-root 2;
        }
      }
      description
        "none";
    }
    description
      "none";
  }

  grouping oam-job-ref {
    leaf oam-job-uuid {
      type leafref {
        path "/ncs:devices/ncs:device/ncs:config/tapi-common:context/tapi-oam:oam-context/tapi-oam:oam-job/tapi-oam:uuid" {
          tailf:xpath-root 3;
        }
      }
      description
        "none";
    }
    description
      "none";
  }

  grouping pm-current-data-ref {
    uses oam-job-ref;
    leaf pm-current-data-local-id {
      type leafref {
        path "/ncs:devices/ncs:device/ncs:live-status/tapi-common:context/tapi-oam:oam-context/tapi-oam:oam-job/tapi-oam:pm-current-data/tapi-oam:local-id" {
          tailf:xpath-root 2;
        }
      }
      description
        "none";
    }
    description
      "none";
  }

  grouping pm-history-data-ref {
    uses pm-current-data-ref;
    leaf pm-history-data-local-id {
      type leafref {
        path "/ncs:devices/ncs:device/ncs:live-status/tapi-common:context/tapi-oam:oam-context/tapi-oam:oam-job/tapi-oam:pm-current-data/tapi-oam:pm-history-data/tapi-oam:local-id" {
          tailf:xpath-root 2;
        }
      }
      description
        "none";
    }
    description
      "none";
  }

  grouping oam-profile-ref {
    leaf oam-profile-uuid {
      type leafref {
        path "/ncs:devices/ncs:device/ncs:config/tapi-common:context/tapi-oam:oam-context/tapi-oam:oam-profile/tapi-oam:uuid" {
          tailf:xpath-root 3;
        }
      }
      description
        "none";
    }
    description
      "none";
  }

  grouping pm-threshold-data-ref {
    uses oam-profile-ref;
    leaf pm-threshold-data-local-id {
      type leafref {
        path "/ncs:devices/ncs:device/ncs:config/tapi-common:context/tapi-oam:oam-context/tapi-oam:oam-profile/tapi-oam:pm-threshold-data/tapi-oam:local-id" {
          tailf:xpath-root 3;
        }
      }
      description
        "none";
    }
    description
      "none";
  }

  grouping pm-bin-data-ref {
    uses oam-profile-ref;
    leaf pm-bin-data-local-id {
      type leafref {
        path "/ncs:devices/ncs:device/ncs:config/tapi-common:context/tapi-oam:oam-context/tapi-oam:oam-profile/tapi-oam:pm-bin-data/tapi-oam:local-id" {
          tailf:xpath-root 3;
        }
      }
      description
        "none";
    }
    description
      "none";
  }

  grouping mep {
    // NCS drop config false leaf 'layer-protocol-name'
    // NCS drop config false leaf direction
    // NCS drop config false leaf 'mep-identifier'
    // NCS drop config false leaf-list 'peer-mep-identifier'
    uses tapi-common:local-class;
    uses tapi-common:operational-state-pac;
    description
      "none";
  }

  grouping oam-job {
    list oam-service-end-point {
      uses oam-service-end-point-ref;
      key "oam-service-uuid oam-service-end-point-local-id";
      min-elements 1;
      description
        "none";
    }
    container oam-profile {
      uses oam-profile-ref;
      description
        "none";
    }
    // NCS drop config false list 'pm-current-data'
    leaf oam-job-type {
      type oam-job-type;
      description
        "none";
    }
    container schedule {
      uses tapi-common:time-range;
      description
        "none";
    }
    // NCS drop config false leaf 'creation-time'
    uses tapi-common:global-class;
    uses tapi-common:admin-state-pac;
    description
      "none";
  }

  grouping meg {
    // NCS drop config false list mep
    // NCS drop config false list mip
    // NCS drop config false leaf 'layer-protocol-name'
    // NCS drop config false leaf direction
    // NCS drop config false leaf 'meg-level'
    // NCS drop config false leaf 'meg-identifier'
    uses tapi-common:resource-spec;
    uses tapi-common:operational-state-pac;
    description
      "none";
  }

  grouping mip {
    // NCS drop config false leaf 'layer-protocol-name'
    uses tapi-common:local-class;
    description
      "none";
  }

  grouping oam-service {
    list end-point {
      key "local-id";
      min-elements 2;
      uses oam-service-end-point;
      description
        "none";
    }
    // NCS drop config false container meg
    container oam-profile {
      uses oam-profile-ref;
      description
        "none";
    }
    uses tapi-common:service-spec;
    uses tapi-common:admin-state-pac;
    uses oam-constraint;
    description
      "none";
  }

  grouping oam-context {
    list oam-service {
      key "uuid";
      uses oam-service;
      description
        "none";
    }
    // NCS drop config false list meg
    list oam-job {
      key "uuid";
      uses oam-job;
      description
        "none";
    }
    list oam-profile {
      key "uuid";
      uses oam-profile;
      description
        "none";
    }
    description
      "none";
  }

  grouping oam-service-end-point {
    container service-interface-point {
      uses tapi-common:service-interface-point-ref;
      description
        "none";
    }
    container connectivity-service-end-point {
      uses tapi-connectivity:connectivity-service-end-point-ref;
      description
        "none";
    }
    // NCS drop config false container mep
    // NCS drop config false container mip
    leaf layer-protocol-name {
      type tapi-common:layer-protocol-name;
      description
        "none";
    }
    leaf direction {
      type tapi-common:port-direction;
      description
        "none";
    }
    leaf mep-identifier {
      type string;
      description
        "This attribute contains the identifier of the MEP.
         This attribute is empty in case the OSEP relates to the provisioing of an MIP.
        ";
    }
    leaf-list peer-mep-identifier {
      type string;
      description
        "This attribute models the MI_PeerMEP_ID[i] defined in G.8021 and configured as specified in G.8051. It provides the identifiers of the MEPs which are peer to the subject MEP.
         This attribute is not specified in case the OSEP relates to the provisioing of an MIP.
         In case of P2P, there is only one peer";
    }
    uses tapi-common:local-class;
    uses tapi-common:admin-state-pac;
    description
      "none";
  }

  grouping mep-mip-list {
    list mip {
      uses mip-ref;
      key "meg-uuid mip-local-id";
      description
        "none";
    }
    list mep {
      uses mep-ref;
      key "meg-uuid mep-local-id";
      description
        "none";
    }
    description
      "none";
  }

  grouping oam-constraint {
    leaf layer-protocol-name {
      type tapi-common:layer-protocol-name;
      description
        "none";
    }
    leaf direction {
      type tapi-common:forwarding-direction;
      description
        "none";
    }
    leaf meg-level {
      type uint64;
      description
        "none";
    }
    description
      "none";
  }

  grouping pm-current-data {
    // NCS drop config false list 'pm-history-data'
    container granularity-period {
      uses tapi-common:time-period;
      description
        "none";
    }
    // NCS drop config false leaf timestamp
    container elapsed-time {
      uses tapi-common:time-interval;
      description
        "none";
    }
    leaf suspect-interval-flag {
      type boolean;
      description
        "This attribute is used to indicate that the performance data for the current period may not be reliable. Some reasons for this to occur are:
         - Suspect data were detected by the actual resource doing data collection.
         - Transition of the administrativeState attribute to/from the 'lock' state.
         - Transition of the operationalState to/from the 'disabled' state.
         - Scheduler setting that inhibits the collection function.
         - The performance counters were reset during the interval.
         - The currentData (or subclass) object instance was created during the monitoring period.";
    }
    uses tapi-common:local-class;
    description
      "none";
  }

  grouping pm-history-data {
    container granularity-period {
      uses tapi-common:time-period;
      description
        "none";
    }
    leaf period-end-time {
      type tapi-common:date-and-time;
      description
        "none";
    }
    // NCS drop config false leaf 'suspect-interval-flag'
    uses tapi-common:local-class;
    description
      "none";
  }

  grouping oam-profile {
    list pm-threshold-data {
      key "local-id";
      min-elements 1;
      uses pm-threshold-data;
      description
        "none";
    }
    list pm-bin-data {
      key "local-id";
      min-elements 1;
      uses pm-bin-data;
      description
        "none";
    }
    uses tapi-common:global-class;
    description
      "none";
  }

  grouping pm-threshold-data {
    container granularity-period {
      uses tapi-common:time-period;
      description
        "none";
    }
    leaf is-transient {
      type boolean;
      description
        "none";
    }
    uses tapi-common:local-class;
    description
      "none";
  }

  grouping pm-bin-data {
    container granularity-period {
      uses tapi-common:time-period;
      description
        "none";
    }
    uses tapi-common:local-class;
    description
      "none";
  }

  augment "/ncs:devices/ncs:device/ncs:rpc" {
    container rpc-get-oam-service-end-point {
      tailf:ncs-device-type "netconf";
      tailf:display-when "not(../../ncs:module) or ../../ncs:module[ncs:name='tapi-oam']";
      tailf:action get-oam-service-end-point {
        tailf:actionpoint ncsproxy {
          tailf:internal;
        }
        description
          "none";
        input {
          leaf service-id {
            type string;
            description
              "none";
          }
          leaf o-sep-id {
            type string;
            description
              "none";
          }
        }
        output {
          container end-point {
            uses ncs_rpc_notif_oam-service-end-point;
            description
              "none";
          }
        }
      }
    }
  }
  augment "/ncs:devices/ncs:device-group/ncs:ned-id/ncs:rpc" {
    container rpc-get-oam-service-end-point {
      tailf:ncs-device-type "netconf";
      tailf:display-when "../../ncs:id = 'onf-tapi-nc-2.0:onf-tapi-nc-2.0'";
      tailf:action get-oam-service-end-point {
        tailf:actionpoint ncsproxy {
          tailf:internal;
        }
        description
          "none";
        input {
          leaf service-id {
            type string;
            description
              "none";
          }
          leaf o-sep-id {
            type string;
            description
              "none";
          }
        }
        output {
          container "device" {
            leaf "name" {
              type string;
            }
            leaf "info" {
              type string;
            }
            container "result" {
              container end-point {
                uses ncs_rpc_notif_oam-service-end-point;
                description
                  "none";
              }
            }
          }
        }
      }
    }
  }
  augment "/ncs:devices/ncs:device/ncs:rpc" {
    container rpc-update-oam-service-end-point {
      tailf:ncs-device-type "netconf";
      tailf:display-when "not(../../ncs:module) or ../../ncs:module[ncs:name='tapi-oam']";
      tailf:action update-oam-service-end-point {
        tailf:actionpoint ncsproxy {
          tailf:internal;
        }
        description
          "none";
        input {
          leaf service-id {
            type string;
            description
              "none";
          }
          leaf o-sep-id {
            type string;
            description
              "none";
          }
          leaf state {
            type string;
            description
              "none";
          }
        }
        output {
          container end-point {
            uses ncs_rpc_notif_oam-service-end-point;
            description
              "none";
          }
        }
      }
    }
  }
  augment "/ncs:devices/ncs:device-group/ncs:ned-id/ncs:rpc" {
    container rpc-update-oam-service-end-point {
      tailf:ncs-device-type "netconf";
      tailf:display-when "../../ncs:id = 'onf-tapi-nc-2.0:onf-tapi-nc-2.0'";
      tailf:action update-oam-service-end-point {
        tailf:actionpoint ncsproxy {
          tailf:internal;
        }
        description
          "none";
        input {
          leaf service-id {
            type string;
            description
              "none";
          }
          leaf o-sep-id {
            type string;
            description
              "none";
          }
          leaf state {
            type string;
            description
              "none";
          }
        }
        output {
          container "device" {
            leaf "name" {
              type string;
            }
            leaf "info" {
              type string;
            }
            container "result" {
              container end-point {
                uses ncs_rpc_notif_oam-service-end-point;
                description
                  "none";
              }
            }
          }
        }
      }
    }
  }
  augment "/ncs:devices/ncs:device/ncs:rpc" {
    container rpc-delete-oam-service-end-point {
      tailf:ncs-device-type "netconf";
      tailf:display-when "not(../../ncs:module) or ../../ncs:module[ncs:name='tapi-oam']";
      tailf:action delete-oam-service-end-point {
        tailf:actionpoint ncsproxy {
          tailf:internal;
        }
        description
          "none";
        input {
          leaf service-id {
            type string;
            description
              "none";
          }
          leaf o-sep-id {
            type string;
            description
              "none";
          }
        }
      }
    }
  }
  augment "/ncs:devices/ncs:device-group/ncs:ned-id/ncs:rpc" {
    container rpc-delete-oam-service-end-point {
      tailf:ncs-device-type "netconf";
      tailf:display-when "../../ncs:id = 'onf-tapi-nc-2.0:onf-tapi-nc-2.0'";
      tailf:action delete-oam-service-end-point {
        tailf:actionpoint ncsproxy {
          tailf:internal;
        }
        description
          "none";
        input {
          leaf service-id {
            type string;
            description
              "none";
          }
          leaf o-sep-id {
            type string;
            description
              "none";
          }
        }
      }
    }
  }
  augment "/ncs:devices/ncs:device/ncs:rpc" {
    container rpc-create-oam-service-end-point {
      tailf:ncs-device-type "netconf";
      tailf:display-when "not(../../ncs:module) or ../../ncs:module[ncs:name='tapi-oam']";
      tailf:action create-oam-service-end-point {
        tailf:actionpoint ncsproxy {
          tailf:internal;
        }
        description
          "none";
        input {
          leaf service-id {
            type string;
            description
              "none";
          }
          leaf sip-id {
            type string;
            description
              "none";
          }
          leaf c-sep-id {
            type string;
            description
              "none";
          }
          leaf layer {
            type string;
            description
              "none";
          }
          leaf direction {
            type string;
            description
              "none";
          }
          leaf state {
            type string;
            description
              "none";
          }
          leaf mep-identifier {
            type string;
            description
              "none";
          }
          leaf-list peer-mep-identifier {
            type string;
            description
              "none";
          }
        }
        output {
          container end-point {
            uses ncs_rpc_notif_oam-service-end-point;
            description
              "none";
          }
        }
      }
    }
  }
  augment "/ncs:devices/ncs:device-group/ncs:ned-id/ncs:rpc" {
    container rpc-create-oam-service-end-point {
      tailf:ncs-device-type "netconf";
      tailf:display-when "../../ncs:id = 'onf-tapi-nc-2.0:onf-tapi-nc-2.0'";
      tailf:action create-oam-service-end-point {
        tailf:actionpoint ncsproxy {
          tailf:internal;
        }
        description
          "none";
        input {
          leaf service-id {
            type string;
            description
              "none";
          }
          leaf sip-id {
            type string;
            description
              "none";
          }
          leaf c-sep-id {
            type string;
            description
              "none";
          }
          leaf layer {
            type string;
            description
              "none";
          }
          leaf direction {
            type string;
            description
              "none";
          }
          leaf state {
            type string;
            description
              "none";
          }
          leaf mep-identifier {
            type string;
            description
              "none";
          }
          leaf-list peer-mep-identifier {
            type string;
            description
              "none";
          }
        }
        output {
          container "device" {
            leaf "name" {
              type string;
            }
            leaf "info" {
              type string;
            }
            container "result" {
              container end-point {
                uses ncs_rpc_notif_oam-service-end-point;
                description
                  "none";
              }
            }
          }
        }
      }
    }
  }
  augment "/ncs:devices/ncs:device/ncs:rpc" {
    container rpc-update-oam-job {
      tailf:ncs-device-type "netconf";
      tailf:display-when "not(../../ncs:module) or ../../ncs:module[ncs:name='tapi-oam']";
      tailf:action update-oam-job {
        tailf:actionpoint ncsproxy {
          tailf:internal;
        }
        description
          "none";
        input {
          leaf job-id {
            type string;
            description
              "none";
          }
          container oam-profile {
            uses ncs_rpc_notif_oam-profile;
            description
              "none";
          }
          leaf state {
            type string;
            description
              "none";
          }
          leaf schedule {
            type string;
            description
              "none";
          }
        }
        output {
          container oam-job {
            uses ncs_rpc_notif_oam-job;
            description
              "none";
          }
        }
      }
    }
  }
  augment "/ncs:devices/ncs:device-group/ncs:ned-id/ncs:rpc" {
    container rpc-update-oam-job {
      tailf:ncs-device-type "netconf";
      tailf:display-when "../../ncs:id = 'onf-tapi-nc-2.0:onf-tapi-nc-2.0'";
      tailf:action update-oam-job {
        tailf:actionpoint ncsproxy {
          tailf:internal;
        }
        description
          "none";
        input {
          leaf job-id {
            type string;
            description
              "none";
          }
          container oam-profile {
            uses ncs_rpc_notif_oam-profile;
            description
              "none";
          }
          leaf state {
            type string;
            description
              "none";
          }
          leaf schedule {
            type string;
            description
              "none";
          }
        }
        output {
          container "device" {
            leaf "name" {
              type string;
            }
            leaf "info" {
              type string;
            }
            container "result" {
              container oam-job {
                uses ncs_rpc_notif_oam-job;
                description
                  "none";
              }
            }
          }
        }
      }
    }
  }
  augment "/ncs:devices/ncs:device/ncs:rpc" {
    container rpc-delete-oam-job {
      tailf:ncs-device-type "netconf";
      tailf:display-when "not(../../ncs:module) or ../../ncs:module[ncs:name='tapi-oam']";
      tailf:action delete-oam-job {
        tailf:actionpoint ncsproxy {
          tailf:internal;
        }
        description
          "none";
        input {
          leaf job-id {
            type string;
            description
              "none";
          }
        }
      }
    }
  }
  augment "/ncs:devices/ncs:device-group/ncs:ned-id/ncs:rpc" {
    container rpc-delete-oam-job {
      tailf:ncs-device-type "netconf";
      tailf:display-when "../../ncs:id = 'onf-tapi-nc-2.0:onf-tapi-nc-2.0'";
      tailf:action delete-oam-job {
        tailf:actionpoint ncsproxy {
          tailf:internal;
        }
        description
          "none";
        input {
          leaf job-id {
            type string;
            description
              "none";
          }
        }
      }
    }
  }
  augment "/ncs:devices/ncs:device/ncs:rpc" {
    container rpc-update-oam-service {
      tailf:ncs-device-type "netconf";
      tailf:display-when "not(../../ncs:module) or ../../ncs:module[ncs:name='tapi-oam']";
      tailf:action update-oam-service {
        tailf:actionpoint ncsproxy {
          tailf:internal;
        }
        description
          "none";
        input {
          leaf service-id {
            type string;
            description
              "none";
          }
          list end-point {
            key "local-id";
            uses ncs_rpc_notif_oam-service-end-point;
            description
              "none";
          }
          container oam-constraint {
            uses ncs_rpc_notif_oam-constraint;
            description
              "none";
          }
          leaf state {
            type string;
            description
              "none";
          }
        }
        output {
          container service {
            uses ncs_rpc_notif_oam-service;
            description
              "none";
          }
        }
      }
    }
  }
  augment "/ncs:devices/ncs:device-group/ncs:ned-id/ncs:rpc" {
    container rpc-update-oam-service {
      tailf:ncs-device-type "netconf";
      tailf:display-when "../../ncs:id = 'onf-tapi-nc-2.0:onf-tapi-nc-2.0'";
      tailf:action update-oam-service {
        tailf:actionpoint ncsproxy {
          tailf:internal;
        }
        description
          "none";
        input {
          leaf service-id {
            type string;
            description
              "none";
          }
          list end-point {
            key "local-id";
            uses ncs_rpc_notif_oam-service-end-point;
            description
              "none";
          }
          container oam-constraint {
            uses ncs_rpc_notif_oam-constraint;
            description
              "none";
          }
          leaf state {
            type string;
            description
              "none";
          }
        }
        output {
          container "device" {
            leaf "name" {
              type string;
            }
            leaf "info" {
              type string;
            }
            container "result" {
              container service {
                uses ncs_rpc_notif_oam-service;
                description
                  "none";
              }
            }
          }
        }
      }
    }
  }
  augment "/ncs:devices/ncs:device/ncs:rpc" {
    container rpc-get-meg {
      tailf:ncs-device-type "netconf";
      tailf:display-when "not(../../ncs:module) or ../../ncs:module[ncs:name='tapi-oam']";
      tailf:action get-meg {
        tailf:actionpoint ncsproxy {
          tailf:internal;
        }
        description
          "none";
        input {
          leaf service-id {
            type string;
            description
              "none";
          }
        }
        output {
          container meg {
            uses ncs_rpc_notif_meg;
            description
              "none";
          }
        }
      }
    }
  }
  augment "/ncs:devices/ncs:device-group/ncs:ned-id/ncs:rpc" {
    container rpc-get-meg {
      tailf:ncs-device-type "netconf";
      tailf:display-when "../../ncs:id = 'onf-tapi-nc-2.0:onf-tapi-nc-2.0'";
      tailf:action get-meg {
        tailf:actionpoint ncsproxy {
          tailf:internal;
        }
        description
          "none";
        input {
          leaf service-id {
            type string;
            description
              "none";
          }
        }
        output {
          container "device" {
            leaf "name" {
              type string;
            }
            leaf "info" {
              type string;
            }
            container "result" {
              container meg {
                uses ncs_rpc_notif_meg;
                description
                  "none";
              }
            }
          }
        }
      }
    }
  }
  augment "/ncs:devices/ncs:device/ncs:rpc" {
    container rpc-get-oam-service-list {
      tailf:ncs-device-type "netconf";
      tailf:display-when "not(../../ncs:module) or ../../ncs:module[ncs:name='tapi-oam']";
      tailf:action get-oam-service-list {
        tailf:actionpoint ncsproxy {
          tailf:internal;
        }
        description
          "none";
        output {
          list service {
            key "uuid";
            uses ncs_rpc_notif_oam-service;
            description
              "none";
          }
        }
      }
    }
  }
  augment "/ncs:devices/ncs:device-group/ncs:ned-id/ncs:rpc" {
    container rpc-get-oam-service-list {
      tailf:ncs-device-type "netconf";
      tailf:display-when "../../ncs:id = 'onf-tapi-nc-2.0:onf-tapi-nc-2.0'";
      tailf:action get-oam-service-list {
        tailf:actionpoint ncsproxy {
          tailf:internal;
        }
        description
          "none";
        output {
          container "device" {
            leaf "name" {
              type string;
            }
            leaf "info" {
              type string;
            }
            container "result" {
              list service {
                key "uuid";
                uses ncs_rpc_notif_oam-service;
                description
                  "none";
              }
            }
          }
        }
      }
    }
  }
  augment "/ncs:devices/ncs:device/ncs:rpc" {
    container rpc-get-oam-job {
      tailf:ncs-device-type "netconf";
      tailf:display-when "not(../../ncs:module) or ../../ncs:module[ncs:name='tapi-oam']";
      tailf:action get-oam-job {
        tailf:actionpoint ncsproxy {
          tailf:internal;
        }
        description
          "none";
        input {
          leaf job-id {
            type string;
            description
              "none";
          }
        }
        output {
          container oam-job {
            uses ncs_rpc_notif_oam-job;
            description
              "none";
          }
        }
      }
    }
  }
  augment "/ncs:devices/ncs:device-group/ncs:ned-id/ncs:rpc" {
    container rpc-get-oam-job {
      tailf:ncs-device-type "netconf";
      tailf:display-when "../../ncs:id = 'onf-tapi-nc-2.0:onf-tapi-nc-2.0'";
      tailf:action get-oam-job {
        tailf:actionpoint ncsproxy {
          tailf:internal;
        }
        description
          "none";
        input {
          leaf job-id {
            type string;
            description
              "none";
          }
        }
        output {
          container "device" {
            leaf "name" {
              type string;
            }
            leaf "info" {
              type string;
            }
            container "result" {
              container oam-job {
                uses ncs_rpc_notif_oam-job;
                description
                  "none";
              }
            }
          }
        }
      }
    }
  }
  augment "/ncs:devices/ncs:device/ncs:rpc" {
    container rpc-create-oam-job {
      tailf:ncs-device-type "netconf";
      tailf:display-when "not(../../ncs:module) or ../../ncs:module[ncs:name='tapi-oam']";
      tailf:action create-oam-job {
        tailf:actionpoint ncsproxy {
          tailf:internal;
        }
        description
          "none";
        input {
          leaf oam-job-type {
            type ncs_rpc_notif_oam-job-type;
            description
              "none";
          }
          list oam-service-end-point {
            key "local-id";
            min-elements 2;
            uses ncs_rpc_notif_oam-service-end-point;
            description
              "none";
          }
          container oam-profile {
            uses ncs_rpc_notif_oam-profile;
            description
              "none";
          }
          leaf state {
            type string;
            description
              "none";
          }
          leaf schedule {
            type string;
            description
              "none";
          }
        }
        output {
          container oam-job {
            uses ncs_rpc_notif_oam-job;
            description
              "none";
          }
        }
      }
    }
  }
  augment "/ncs:devices/ncs:device-group/ncs:ned-id/ncs:rpc" {
    container rpc-create-oam-job {
      tailf:ncs-device-type "netconf";
      tailf:display-when "../../ncs:id = 'onf-tapi-nc-2.0:onf-tapi-nc-2.0'";
      tailf:action create-oam-job {
        tailf:actionpoint ncsproxy {
          tailf:internal;
        }
        description
          "none";
        input {
          leaf oam-job-type {
            type ncs_rpc_notif_oam-job-type;
            description
              "none";
          }
          list oam-service-end-point {
            key "local-id";
            min-elements 2;
            uses ncs_rpc_notif_oam-service-end-point;
            description
              "none";
          }
          container oam-profile {
            uses ncs_rpc_notif_oam-profile;
            description
              "none";
          }
          leaf state {
            type string;
            description
              "none";
          }
          leaf schedule {
            type string;
            description
              "none";
          }
        }
        output {
          container "device" {
            leaf "name" {
              type string;
            }
            leaf "info" {
              type string;
            }
            container "result" {
              container oam-job {
                uses ncs_rpc_notif_oam-job;
                description
                  "none";
              }
            }
          }
        }
      }
    }
  }
  augment "/ncs:devices/ncs:device/ncs:rpc" {
    container rpc-get-oam-service {
      tailf:ncs-device-type "netconf";
      tailf:display-when "not(../../ncs:module) or ../../ncs:module[ncs:name='tapi-oam']";
      tailf:action get-oam-service {
        tailf:actionpoint ncsproxy {
          tailf:internal;
        }
        description
          "none";
        input {
          leaf service-id {
            type string;
            description
              "none";
          }
        }
        output {
          container service {
            uses ncs_rpc_notif_oam-service;
            description
              "none";
          }
        }
      }
    }
  }
  augment "/ncs:devices/ncs:device-group/ncs:ned-id/ncs:rpc" {
    container rpc-get-oam-service {
      tailf:ncs-device-type "netconf";
      tailf:display-when "../../ncs:id = 'onf-tapi-nc-2.0:onf-tapi-nc-2.0'";
      tailf:action get-oam-service {
        tailf:actionpoint ncsproxy {
          tailf:internal;
        }
        description
          "none";
        input {
          leaf service-id {
            type string;
            description
              "none";
          }
        }
        output {
          container "device" {
            leaf "name" {
              type string;
            }
            leaf "info" {
              type string;
            }
            container "result" {
              container service {
                uses ncs_rpc_notif_oam-service;
                description
                  "none";
              }
            }
          }
        }
      }
    }
  }
  augment "/ncs:devices/ncs:device/ncs:rpc" {
    container rpc-delete-oam-service {
      tailf:ncs-device-type "netconf";
      tailf:display-when "not(../../ncs:module) or ../../ncs:module[ncs:name='tapi-oam']";
      tailf:action delete-oam-service {
        tailf:actionpoint ncsproxy {
          tailf:internal;
        }
        description
          "none";
        input {
          leaf service-id {
            type string;
            description
              "none";
          }
        }
      }
    }
  }
  augment "/ncs:devices/ncs:device-group/ncs:ned-id/ncs:rpc" {
    container rpc-delete-oam-service {
      tailf:ncs-device-type "netconf";
      tailf:display-when "../../ncs:id = 'onf-tapi-nc-2.0:onf-tapi-nc-2.0'";
      tailf:action delete-oam-service {
        tailf:actionpoint ncsproxy {
          tailf:internal;
        }
        description
          "none";
        input {
          leaf service-id {
            type string;
            description
              "none";
          }
        }
      }
    }
  }
  augment "/ncs:devices/ncs:device/ncs:rpc" {
    container rpc-create-oam-service {
      tailf:ncs-device-type "netconf";
      tailf:display-when "not(../../ncs:module) or ../../ncs:module[ncs:name='tapi-oam']";
      tailf:action create-oam-service {
        tailf:actionpoint ncsproxy {
          tailf:internal;
        }
        description
          "none";
        input {
          list end-point {
            key "local-id";
            min-elements 2;
            uses ncs_rpc_notif_oam-service-end-point;
            description
              "none";
          }
          container oam-constraint {
            uses ncs_rpc_notif_oam-constraint;
            description
              "none";
          }
          leaf state {
            type string;
            description
              "none";
          }
        }
        output {
          container service {
            uses ncs_rpc_notif_oam-service;
            description
              "none";
          }
        }
      }
    }
  }
  augment "/ncs:devices/ncs:device-group/ncs:ned-id/ncs:rpc" {
    container rpc-create-oam-service {
      tailf:ncs-device-type "netconf";
      tailf:display-when "../../ncs:id = 'onf-tapi-nc-2.0:onf-tapi-nc-2.0'";
      tailf:action create-oam-service {
        tailf:actionpoint ncsproxy {
          tailf:internal;
        }
        description
          "none";
        input {
          list end-point {
            key "local-id";
            min-elements 2;
            uses ncs_rpc_notif_oam-service-end-point;
            description
              "none";
          }
          container oam-constraint {
            uses ncs_rpc_notif_oam-constraint;
            description
              "none";
          }
          leaf state {
            type string;
            description
              "none";
          }
        }
        output {
          container "device" {
            leaf "name" {
              type string;
            }
            leaf "info" {
              type string;
            }
            container "result" {
              container service {
                uses ncs_rpc_notif_oam-service;
                description
                  "none";
              }
            }
          }
        }
      }
    }
  }
  augment "/ncs:devices/ncs:template/ncs:ned-id/ncs:config/tapi-common:context" {
    container oam-context {
      uses ncs_template_oam-context;
      description
        "Augments the base TAPI Context with OamService information";
    }
    description
      "Augments the base TAPI Context with OamService information";
  }
  augment "/ncs:devices/ncs:device/ncs:live-status/tapi-common:context" {
    container oam-context {
      tailf:ncs-device-type "netconf";
      tailf:display-when "not(../../../ncs:module) or ../../../ncs:module[ncs:name='tapi-oam'] or (../../../ncs:live-status-protocol[not(ncs:capability)]) or (../../../ncs:live-status-protocol/ncs:capability/ncs:module[.='tapi-oam'])";
      uses live_ncs_oam-context;
      description
        "Augments the base TAPI Context with OamService information";
    }
    description
      "Augments the base TAPI Context with OamService information";
  }
  augment "/ncs:devices/ncs:device/ncs:config/tapi-common:context" {
    container oam-context {
      tailf:ncs-device-type "netconf";
      tailf:display-when "not(../../../ncs:module) or ../../../ncs:module[ncs:name='tapi-oam']";
      uses oam-context;
      description
        "Augments the base TAPI Context with OamService information";
    }
    description
      "Augments the base TAPI Context with OamService information";
  }
  augment "/ncs:devices/ncs:device/ncs:live-status/tapi-common:context/tapi-topology:topology-context/tapi-topology:topology/tapi-topology:node/tapi-topology:owned-node-edge-point/tapi-connectivity:cep-list/tapi-connectivity:connection-end-point" {
    container mep-mip-list {
      tailf:ncs-device-type "netconf";
      tailf:display-when "not(../../../../../../../../../ncs:module) or ../../../../../../../../../ncs:module[ncs:name='tapi-oam'] or (../../../../../../../../../ncs:live-status-protocol[not(ncs:capability)]) or (../../../../../../../../../ncs:live-status-protocol/ncs:capability/ncs:module[.='tapi-oam'])";
      uses live_ncs_mep-mip-list;
      description
        "none";
    }
    description
      "none";
  }

  identity OAM_JOB_TYPE {
    description
      "none";
  }
}
