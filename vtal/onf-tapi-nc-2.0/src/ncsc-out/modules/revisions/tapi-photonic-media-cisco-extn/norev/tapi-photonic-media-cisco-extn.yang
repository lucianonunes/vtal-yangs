module tapi-photonic-media-cisco-extn {
  // Generated by yanger -t ncs
  tailf:mount-id "onf-tapi-nc-2.0:onf-tapi-nc-2.0";
  tailf:ncs-device-type "netconf";

  yang-version 1.1;
  namespace "http://cisco.com/yang/conc/tapi/photonic-media-extn";
  prefix tapi-photonic-media-cisco-extn;

  import tapi-common {
    prefix tapi-common;
  }
  import tapi-connectivity {
    prefix tapi-connectivity;
  }
  import tapi-topology {
    prefix tapi-topology;
  }
  import tapi-photonic-media {
    prefix tapi-photonic-media;
  }
  import tailf-common {
    prefix tailf;
  }
  import tailf-ncs {
    prefix ncs;
  }

  grouping ncs_template_media-channel-properties-pac {
    // NCS drop config false container 'media-channel-pm-history-data'
  }

  grouping ncs_template_ots-media-channel-properties-pac {
    // NCS drop config false container 'ots-media-channel-pm-history-data'
    // NCS drop config false container 'live-power-data'
  }

  grouping ncs_template_live-power-data {
    description
      "none";
  }

  grouping ncs_template_media-channel-pm-history-data {
    uses ncs_template_pm-data-pac;
    uses ncs_template_pm-power-history-data;
    description
      "none";
  }

  grouping ncs_template_ots-media-channel-pm-history-data {
    uses ncs_template_pm-data-pac;
    // NCS drop config false container 'c-band'
    description
      "none";
  }

  grouping ncs_template_pm-power-history-data {
    // NCS drop config false container 'history-power-ingress'
    // NCS drop config false container 'history-power-egress'
    description
      "none";
  }

  grouping ncs_template_pm-power-parameters-pac {
    // NCS drop config false leaf 'avg-power'
    // NCS drop config false leaf 'min-power'
    // NCS drop config false leaf 'max-power'
    description
      "none";
  }

  grouping ncs_template_pm-data-pac {
    leaf period-start-time {
      type tapi-common:ncs_template_date-and-time;
      description
        "none";
    }
    leaf period-end-time {
      type tapi-common:ncs_template_date-and-time;
      description
        "none";
    }
    // NCS drop config false leaf 'suspect-interval-flag'
    description
      "none";
  }

  grouping ncs_rpc_notif_media-channel-properties-pac {
    container media-channel-pm-history-data {
      config false;
      uses ncs_rpc_notif_media-channel-pm-history-data;
      description
        "none";
    }
  }

  grouping ncs_rpc_notif_ots-media-channel-properties-pac {
    container ots-media-channel-pm-history-data {
      config false;
      uses ncs_rpc_notif_ots-media-channel-pm-history-data;
      description
        "none";
    }
    container live-power-data {
      config false;
      uses ncs_rpc_notif_live-power-data;
      description
        "none";
    }
  }

  grouping ncs_rpc_notif_live-power-data {
    description
      "none";
  }

  grouping ncs_rpc_notif_media-channel-pm-history-data {
    uses ncs_rpc_notif_pm-data-pac;
    uses ncs_rpc_notif_pm-power-history-data;
    description
      "none";
  }

  grouping ncs_rpc_notif_ots-media-channel-pm-history-data {
    uses ncs_rpc_notif_pm-data-pac;
    container c-band {
      config false;
      uses ncs_rpc_notif_pm-power-history-data;
      description
        "none";
    }
    description
      "none";
  }

  grouping ncs_rpc_notif_pm-power-history-data {
    container history-power-ingress {
      config false;
      uses ncs_rpc_notif_pm-power-parameters-pac;
      description
        "none";
    }
    container history-power-egress {
      config false;
      uses ncs_rpc_notif_pm-power-parameters-pac;
      description
        "none";
    }
    description
      "none";
  }

  grouping ncs_rpc_notif_pm-power-parameters-pac {
    leaf avg-power {
      type decimal64 {
        fraction-digits 7;
      }
      config false;
      description
        "The average power for the pm interval specified in dBm.";
    }
    leaf min-power {
      type decimal64 {
        fraction-digits 7;
      }
      config false;
      description
        "The minimum power for the pm interval specified in dBm.";
    }
    leaf max-power {
      type decimal64 {
        fraction-digits 7;
      }
      config false;
      description
        "The maximum power for the pm interval specified in dBm.";
    }
    description
      "none";
  }

  grouping ncs_rpc_notif_pm-data-pac {
    leaf period-start-time {
      type tapi-common:ncs_rpc_notif_date-and-time;
      description
        "none";
    }
    leaf period-end-time {
      type tapi-common:ncs_rpc_notif_date-and-time;
      description
        "none";
    }
    leaf suspect-interval-flag {
      type boolean;
      config false;
      description
        "This attribute indicates that the performance data may not be reliable.";
    }
    description
      "none";
  }

  grouping live_ncs_media-channel-properties-pac {
    container media-channel-pm-history-data {
      uses live_ncs_media-channel-pm-history-data;
      description
        "none";
    }
  }

  grouping live_ncs_ots-media-channel-properties-pac {
    container ots-media-channel-pm-history-data {
      uses live_ncs_ots-media-channel-pm-history-data;
      description
        "none";
    }
    container live-power-data {
      uses live_ncs_live-power-data;
      description
        "none";
    }
  }

  grouping live_ncs_live-power-data {
    action get-live-power-data {
      tailf:actionpoint ncsproxy {
        tailf:internal;
      }
      // NCS drop tailf:actionpoint
      output {
        container measured-power-egress {
          uses tapi-photonic-media:live_ncs_power-properties-pac;
        }
        container measured-power-ingress {
          uses tapi-photonic-media:live_ncs_power-properties-pac;
        }
      }
    }
    description
      "none";
  }

  grouping live_ncs_media-channel-pm-history-data {
    uses live_ncs_pm-data-pac;
    uses live_ncs_pm-power-history-data;
    description
      "none";
  }

  grouping live_ncs_ots-media-channel-pm-history-data {
    uses live_ncs_pm-data-pac;
    container c-band {
      uses live_ncs_pm-power-history-data;
      description
        "none";
    }
    description
      "none";
  }

  grouping live_ncs_pm-power-history-data {
    container history-power-ingress {
      uses live_ncs_pm-power-parameters-pac;
      description
        "none";
    }
    container history-power-egress {
      uses live_ncs_pm-power-parameters-pac;
      description
        "none";
    }
    description
      "none";
  }

  grouping live_ncs_pm-power-parameters-pac {
    leaf avg-power {
      type decimal64 {
        fraction-digits 7;
      }
      description
        "The average power for the pm interval specified in dBm.";
    }
    leaf min-power {
      type decimal64 {
        fraction-digits 7;
      }
      description
        "The minimum power for the pm interval specified in dBm.";
    }
    leaf max-power {
      type decimal64 {
        fraction-digits 7;
      }
      description
        "The maximum power for the pm interval specified in dBm.";
    }
    description
      "none";
  }

  grouping live_ncs_pm-data-pac {
    leaf period-start-time {
      type tapi-common:live_ncs_date-and-time;
      description
        "none";
    }
    leaf period-end-time {
      type tapi-common:live_ncs_date-and-time;
      description
        "none";
    }
    leaf suspect-interval-flag {
      type boolean;
      description
        "This attribute indicates that the performance data may not be reliable.";
    }
    description
      "none";
  }

  grouping media-channel-properties-pac {
    // NCS drop config false container 'media-channel-pm-history-data'
  }

  grouping ots-media-channel-properties-pac {
    // NCS drop config false container 'ots-media-channel-pm-history-data'
    // NCS drop config false container 'live-power-data'
  }

  grouping live-power-data {
    action get-live-power-data {
      tailf:actionpoint ncsproxy {
        tailf:internal;
      }
      // NCS drop tailf:actionpoint
      output {
        container measured-power-egress {
          uses tapi-photonic-media:power-properties-pac;
        }
        container measured-power-ingress {
          uses tapi-photonic-media:power-properties-pac;
        }
      }
    }
    description
      "none";
  }

  grouping media-channel-pm-history-data {
    uses pm-data-pac;
    uses pm-power-history-data;
    description
      "none";
  }

  grouping ots-media-channel-pm-history-data {
    uses pm-data-pac;
    // NCS drop config false container 'c-band'
    description
      "none";
  }

  grouping pm-power-history-data {
    // NCS drop config false container 'history-power-ingress'
    // NCS drop config false container 'history-power-egress'
    description
      "none";
  }

  grouping pm-power-parameters-pac {
    // NCS drop config false leaf 'avg-power'
    // NCS drop config false leaf 'min-power'
    // NCS drop config false leaf 'max-power'
    description
      "none";
  }

  grouping pm-data-pac {
    leaf period-start-time {
      type tapi-common:date-and-time;
      description
        "none";
    }
    leaf period-end-time {
      type tapi-common:date-and-time;
      description
        "none";
    }
    // NCS drop config false leaf 'suspect-interval-flag'
    description
      "none";
  }

  augment "/ncs:devices/ncs:device/ncs:live-status/tapi-common:context/tapi-topology:topology-context/tapi-topology:topology/tapi-topology:node/tapi-topology:owned-node-edge-point/tapi-connectivity:cep-list/tapi-connectivity:connection-end-point/tapi-photonic-media:media-channel-connection-end-point-spec/tapi-photonic-media:media-channel" {
    container media-channel {
      tailf:ncs-device-type "netconf";
      tailf:display-when "not(../../../../../../../../../../../ncs:module) or ../../../../../../../../../../../ncs:module[ncs:name='tapi-photonic-media-cisco-extn'] or (../../../../../../../../../../../ncs:live-status-protocol[not(ncs:capability)]) or (../../../../../../../../../../../ncs:live-status-protocol/ncs:capability/ncs:module[.='tapi-photonic-media-cisco-extn'])";
      uses live_ncs_media-channel-properties-pac;
      description
        "none";
    }
    description
      "none";
  }
  augment "/ncs:devices/ncs:device/ncs:live-status/tapi-common:context/tapi-topology:topology-context/tapi-topology:topology/tapi-topology:node/tapi-topology:owned-node-edge-point/tapi-connectivity:cep-list/tapi-connectivity:connection-end-point/tapi-photonic-media:ots-connection-end-point-spec/tapi-photonic-media:ots-media-channel" {
    container ots-media-channel {
      tailf:ncs-device-type "netconf";
      tailf:display-when "not(../../../../../../../../../../../ncs:module) or ../../../../../../../../../../../ncs:module[ncs:name='tapi-photonic-media-cisco-extn'] or (../../../../../../../../../../../ncs:live-status-protocol[not(ncs:capability)]) or (../../../../../../../../../../../ncs:live-status-protocol/ncs:capability/ncs:module[.='tapi-photonic-media-cisco-extn'])";
      uses live_ncs_ots-media-channel-properties-pac;
      description
        "none";
    }
    description
      "none";
  }
}
