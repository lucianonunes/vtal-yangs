module tailf-netconf-forward {
  // Generated by yanger -t ncs
  tailf:mount-id "onf-tapi-nc-2.0:onf-tapi-nc-2.0";
  tailf:ncs-device-type "netconf";

  yang-version 1.1;
  namespace "http://tail-f.com/ns/netconf/forward/1.0";
  prefix fwd;

  import ietf-inet-types {
    prefix inet;
  }
  import tailf-common {
    prefix tailf;
  }
  import tailf-ncs {
    prefix ncs;
  }

  description
    "Copyright 2019 Cisco Systems, Inc.
     All rights reserved.
     Permission is hereby granted to redistribute this file without
     modification.";

  grouping ncs_template_sasl-failure-type {
    container failure {
      choice reason {
        leaf incorrect-encoding {
          type empty;
        }
        leaf invalid-authzid {
          type empty;
        }
        leaf invalid-mechanism {
          type empty;
        }
        leaf mechanism-too-weak {
          type empty;
        }
        leaf not-authorized {
          type empty;
        }
        leaf temporary-auth-failure {
          type empty;
        }
      }
    }
  }

  grouping ncs_template_forward-response-type {
    choice result {
      case connected {
        container capabilities {
          description
            "The capabilities of the target NETCONF server.";
          leaf-list capability {
            // NCS patched for predictable order
            ordered-by user;
            type string;
          }
        }
      }
      case challenge {
        container challenge {
          description
            "Sent when the forwarding request failed because the
             target server challenged the authentication request.

             The challenge response is sent as the 'response'
             parameter in the 'challenge-response' rpc.";
          leaf challenge {
            type string;
          }
        }
      }
    }
  }

  grouping ncs_rpc_notif_sasl-failure-type {
    container failure {
      choice reason {
        leaf incorrect-encoding {
          type empty;
        }
        leaf invalid-authzid {
          type empty;
        }
        leaf invalid-mechanism {
          type empty;
        }
        leaf mechanism-too-weak {
          type empty;
        }
        leaf not-authorized {
          type empty;
        }
        leaf temporary-auth-failure {
          type empty;
        }
      }
    }
  }

  grouping ncs_rpc_notif_forward-response-type {
    choice result {
      case connected {
        container capabilities {
          description
            "The capabilities of the target NETCONF server.";
          leaf-list capability {
            type inet:uri;
          }
        }
      }
      case challenge {
        container challenge {
          description
            "Sent when the forwarding request failed because the
             target server challenged the authentication request.

             The challenge response is sent as the 'response'
             parameter in the 'challenge-response' rpc.";
          leaf challenge {
            type string;
          }
        }
      }
    }
  }

  grouping live_ncs_sasl-failure-type {
    container failure {
      choice reason {
        leaf incorrect-encoding {
          type empty;
        }
        leaf invalid-authzid {
          type empty;
        }
        leaf invalid-mechanism {
          type empty;
        }
        leaf mechanism-too-weak {
          type empty;
        }
        leaf not-authorized {
          type empty;
        }
        leaf temporary-auth-failure {
          type empty;
        }
      }
    }
  }

  grouping live_ncs_forward-response-type {
    choice result {
      case connected {
        container capabilities {
          description
            "The capabilities of the target NETCONF server.";
          leaf-list capability {
            type inet:uri;
          }
        }
      }
      case challenge {
        container challenge {
          description
            "Sent when the forwarding request failed because the
             target server challenged the authentication request.

             The challenge response is sent as the 'response'
             parameter in the 'challenge-response' rpc.";
          leaf challenge {
            type string;
          }
        }
      }
    }
  }

  grouping sasl-failure-type {
    container failure {
      choice reason {
        leaf incorrect-encoding {
          type empty;
        }
        leaf invalid-authzid {
          type empty;
        }
        leaf invalid-mechanism {
          type empty;
        }
        leaf mechanism-too-weak {
          type empty;
        }
        leaf not-authorized {
          type empty;
        }
        leaf temporary-auth-failure {
          type empty;
        }
      }
    }
  }

  grouping forward-response-type {
    choice result {
      case connected {
        container capabilities {
          description
            "The capabilities of the target NETCONF server.";
          leaf-list capability {
            type inet:uri;
          }
        }
      }
      case challenge {
        container challenge {
          description
            "Sent when the forwarding request failed because the
             target server challenged the authentication request.

             The challenge response is sent as the 'response'
             parameter in the 'challenge-response' rpc.";
          leaf challenge {
            type string;
          }
        }
      }
    }
  }

  augment "/ncs:devices/ncs:device/ncs:rpc" {
    container rpc-challenge-response {
      tailf:ncs-device-type "netconf";
      tailf:display-when "not(../../ncs:module) or ../../ncs:module[ncs:name='tailf-netconf-forward']";
      tailf:action challenge-response {
        tailf:actionpoint ncsproxy {
          tailf:internal;
        }
        input {
          leaf response {
            type string;
            mandatory true;
          }
        }
        output {
          uses ncs_rpc_notif_forward-response-type;
        }
        description
          "May return 'sasl-failure' error.";
      }
    }
  }
  augment "/ncs:devices/ncs:device-group/ncs:ned-id/ncs:rpc" {
    container rpc-challenge-response {
      tailf:ncs-device-type "netconf";
      tailf:display-when "../../ncs:id = 'onf-tapi-nc-2.0:onf-tapi-nc-2.0'";
      tailf:action challenge-response {
        tailf:actionpoint ncsproxy {
          tailf:internal;
        }
        input {
          leaf response {
            type string;
            mandatory true;
          }
        }
        output {
          container "device" {
            leaf "name" {
              type string;
            }
            leaf "info" {
              type string;
            }
            container "result" {
              uses ncs_rpc_notif_forward-response-type;
            }
          }
        }
        description
          "May return 'sasl-failure' error.";
      }
    }
  }
  augment "/ncs:devices/ncs:device/ncs:rpc" {
    container rpc-forward {
      tailf:ncs-device-type "netconf";
      tailf:display-when "not(../../ncs:module) or ../../ncs:module[ncs:name='tailf-netconf-forward']";
      tailf:action forward {
        tailf:actionpoint ncsproxy {
          tailf:internal;
        }
        input {
          leaf target {
            type string;
            mandatory true;
          }
          container auth {
            presence "Provides authentication parameters";
            leaf mechanism {
              type string;
              mandatory true;
            }
            leaf initial-response {
              type string;
            }
          }
        }
        output {
          uses ncs_rpc_notif_forward-response-type;
        }
        description
          "May return 'connection-failure', 'sasl-authentication-needed', or
           'sasl-failure' error.";
      }
    }
  }
  augment "/ncs:devices/ncs:device-group/ncs:ned-id/ncs:rpc" {
    container rpc-forward {
      tailf:ncs-device-type "netconf";
      tailf:display-when "../../ncs:id = 'onf-tapi-nc-2.0:onf-tapi-nc-2.0'";
      tailf:action forward {
        tailf:actionpoint ncsproxy {
          tailf:internal;
        }
        input {
          leaf target {
            type string;
            mandatory true;
          }
          container auth {
            presence "Provides authentication parameters";
            leaf mechanism {
              type string;
              mandatory true;
            }
            leaf initial-response {
              type string;
            }
          }
        }
        output {
          container "device" {
            leaf "name" {
              type string;
            }
            leaf "info" {
              type string;
            }
            container "result" {
              uses ncs_rpc_notif_forward-response-type;
            }
          }
        }
        description
          "May return 'connection-failure', 'sasl-authentication-needed', or
           'sasl-failure' error.";
      }
    }
  }
  tailf:error-info {
    container connection-failure {
      description
        "The error-message element MAY contain a human readable reason
         for the connection failure.";
      leaf error {
        type string;
        description
          "A POSIX error name or one of:
             subsystem-not-supported
          ";
      }
    }
    container sasl-authentication-needed {
      description
        "Sent when the forwarding request failed because the no
         suitable authentication mechanism was present in the
         forwarding request.";
      container mechanisms {
        leaf-list mechanism {
          type string;
        }
      }
    }
    container sasl-failure {
      uses sasl-failure-type;
    }
  }
}
