module tapi-odu {
  // Generated by yanger -t ncs
  tailf:mount-id "onf-tapi-nc-2.0:onf-tapi-nc-2.0";
  tailf:ncs-device-type "netconf";

  namespace "urn:onf:otcc:yang:tapi-odu";
  prefix tapi-odu;

  import tapi-common {
    prefix tapi-common;
  }
  import tapi-connectivity {
    prefix tapi-connectivity;
  }
  import tapi-topology {
    prefix tapi-topology;
  }
  import tapi-oam {
    prefix tapi-oam;
  }
  import tapi-dsr {
    prefix tapi-dsr;
  }
  import tailf-common {
    prefix tailf;
  }
  import tailf-ncs {
    prefix ncs;
  }

  organization
    "ONF OTCC (Open Transport Configuration & Control) Project";
  contact
    "
     Project Web: <https://urldefense.com/v3/__https://wiki.opennetworking.org/display/OTCC/TAPI__;!!OSsGDw!d_dJlNtYLmD585It0DKukzB2TS5KZqBZQ-pdI1D-6c6c5hRDotd6G39KDEbL$ >
     Project List: <mailto:transport-api@opennetworking.org>
     Editor: Karthik Sethuraman <mailto:karthik.sethuraman@necam.com>
     Andrea Mazzini <mailto:andrea.mazzini@nokia.com>
     Arturo Mayoral <mailto:arturo.mayoral@telefonica.com>
     Nigel Davis <mailto:ndavis@ciena.com>";
  description
    "
     This module contains TAPI ODU Model definitions.
     Source: TapiOdu.uml
     - The TAPI YANG models included in this TAPI release are a *normative* part of the TAPI SDK.
     - The YANG specifications have been generated from the corresponding UML model using the [ONF EAGLE UML2YANG mapping tool]
     <https://urldefense.com/v3/__https://github.com/OpenNetworkingFoundation/EagleUmlYang__;!!OSsGDw!d_dJlNtYLmD585It0DKukzB2TS5KZqBZQ-pdI1D-6c6c5hRDotd6G4QHf0bG$ >
     and further edited manually to comply with the [ONF IISOMI UML2YANG mapping guidelines]
     <https://urldefense.com/v3/__https://wiki.opennetworking.org/display/OIMT/UML*-*YANG*Guidelines__;Kysr!!OSsGDw!d_dJlNtYLmD585It0DKukzB2TS5KZqBZQ-pdI1D-6c6c5hRDotd6G8IIivez$ >
     - Status of YANG model artifacts can be determined by referring to the corresponding UML artifacts.
     As described in the UML models, some artifacts are considered *experimental*, and thus the corresponding YANG artifacts.
     - The ONF TAPI release process does not guarantee backward compatibility of YANG models across major versions of TAPI releases.
     The YANG model backward compatibility criteria are outlined in section 11 of <https://urldefense.com/v3/__https://tools.ietf.org/html/rfc7950__;!!OSsGDw!d_dJlNtYLmD585It0DKukzB2TS5KZqBZQ-pdI1D-6c6c5hRDotd6G3bKxRf2$ >.
     YANG models included in this release may not be backward compatible with previous TAPI releases.
     Copyright (c) 2018 Open Networking Foundation (ONF). All rights reserved.
     License: This module is distributed under the Apache License 2.0";

  revision 2020-04-23 {
    description
      "ONF Transport API version 2.1.3.
       Changes included in this TAPI release (v2.1.3) are listed in
       <https://urldefense.com/v3/__https://github.com/OpenNetworkingFoundation/TAPI/blob/develop_v2_1/CHANGE_LOG/change-log.2.1.3.md__;!!OSsGDw!d_dJlNtYLmD585It0DKukzB2TS5KZqBZQ-pdI1D-6c6c5hRDotd6G7tqhxFK$ >";
    reference
      "ONF-TR-527, ONF-TR-512, ONF-TR-531, RFC 7950, RFC 6087 and ONF TAPI UML model
       <https://urldefense.com/v3/__https://github.com/OpenNetworkingFoundation/TAPI/tree/v2.1.0/UML__;!!OSsGDw!d_dJlNtYLmD585It0DKukzB2TS5KZqBZQ-pdI1D-6c6c5hRDotd6G7KeAhLL$ >";
  }
  revision 2019-07-16 {
    description
      "ONF Transport API version 2.1.2.
       Changes included in this TAPI release (v2.1.2) are listed in
       <https://urldefense.com/v3/__https://github.com/OpenNetworkingFoundation/TAPI/blob/develop_v2_1/CHANGE_LOG/change-log.2.1.2.md__;!!OSsGDw!d_dJlNtYLmD585It0DKukzB2TS5KZqBZQ-pdI1D-6c6c5hRDotd6G7eDS6-t$ >";
    reference
      "ONF-TR-527, ONF-TR-512, ONF-TR-531, RFC 7950, RFC 6087 and ONF TAPI UML model
       <https://urldefense.com/v3/__https://github.com/OpenNetworkingFoundation/TAPI/tree/v2.1.0/UML__;!!OSsGDw!d_dJlNtYLmD585It0DKukzB2TS5KZqBZQ-pdI1D-6c6c5hRDotd6G7KeAhLL$ >";
  }
  revision 2018-12-10 {
    description
      "ONF Transport API version 2.1.1.
       Changes included in this TAPI release (v2.1.1) are listed in
       <https://urldefense.com/v3/__https://github.com/OpenNetworkingFoundation/TAPI/blob/develop/CHANGE_LOG/change-log.2.1.1.md__;!!OSsGDw!d_dJlNtYLmD585It0DKukzB2TS5KZqBZQ-pdI1D-6c6c5hRDotd6G1ftwU5J$ >";
    reference
      "ONF-TR-527, ONF-TR-512, ONF-TR-531, RFC 7950, RFC 6087 and ONF TAPI UML model
       <https://urldefense.com/v3/__https://github.com/OpenNetworkingFoundation/TAPI/tree/v2.1.0/UML__;!!OSsGDw!d_dJlNtYLmD585It0DKukzB2TS5KZqBZQ-pdI1D-6c6c5hRDotd6G7KeAhLL$ >";
  }
  revision 2018-10-16 {
    description
      "ONF Transport API version 2.1.0.
       Changes included in this TAPI release (v2.1.0) are listed in
       <https://urldefense.com/v3/__https://github.com/OpenNetworkingFoundation/TAPI/blob/develop/CHANGE_LOG/change-log.2.1.0.md__;!!OSsGDw!d_dJlNtYLmD585It0DKukzB2TS5KZqBZQ-pdI1D-6c6c5hRDotd6G-5JStw4$ >";
    reference
      "ONF-TR-527, ONF-TR-512, ONF-TR-531, RFC 7950, RFC 6087 and ONF TAPI UML model
       <https://urldefense.com/v3/__https://github.com/OpenNetworkingFoundation/TAPI/tree/v2.1.0/UML__;!!OSsGDw!d_dJlNtYLmD585It0DKukzB2TS5KZqBZQ-pdI1D-6c6c5hRDotd6G7KeAhLL$ >";
  }
  revision 2018-03-07 {
    description
      "ONF Transport API version 2.0.2
       This YANG module has been generated from the TAPI UML Model using the IISOMI-Eagle xmi2yang mapping tool.
       Changes in this revision: <https://urldefense.com/v3/__https://github.com/OpenNetworkingFoundation/TAPI/blob/develop/CHANGE_LOG/change-log.2.0.2.md__;!!OSsGDw!d_dJlNtYLmD585It0DKukzB2TS5KZqBZQ-pdI1D-6c6c5hRDotd6G1Yf4AAN$ >";
    reference
      "ONF-TR-527, ONF-TR-512, ONF-TR-531, RFC 6020, RFC 6087 and ONF TAPI UML model
       <https://urldefense.com/v3/__https://github.com/OpenNetworkingFoundation/TAPI/tree/v2.0.2/UML__;!!OSsGDw!d_dJlNtYLmD585It0DKukzB2TS5KZqBZQ-pdI1D-6c6c5hRDotd6G27-pJK_$ >";
  }
  revision 2018-02-16 {
    description
      "ONF Transport API version 2.0.1
       This YANG module has been generated from the TAPI UML Model using the IISOMI-Eagle xmi2yang mapping tool.
       Changes in this revision: <https://urldefense.com/v3/__https://github.com/OpenNetworkingFoundation/TAPI/blob/develop/CHANGE_LOG/change-log.2.0.1.md__;!!OSsGDw!d_dJlNtYLmD585It0DKukzB2TS5KZqBZQ-pdI1D-6c6c5hRDotd6G8RnGvXg$ >";
    reference
      "ONF-TR-527, ONF-TR-512, ONF-TR-531, RFC 6020, RFC 6087 and ONF TAPI UML model
       <https://urldefense.com/v3/__https://github.com/OpenNetworkingFoundation/TAPI/tree/v2.0.1/UML__;!!OSsGDw!d_dJlNtYLmD585It0DKukzB2TS5KZqBZQ-pdI1D-6c6c5hRDotd6Gy6YoeAv$ >";
  }
  revision 2018-01-02 {
    description
      "ONF Transport API version 2.0.0
       This YANG module has been generated from the TAPI UML Model using the IISOMI-Eagle xmi2yang mapping tool.
       Changes in this revision: <https://urldefense.com/v3/__https://github.com/OpenNetworkingFoundation/TAPI/blob/develop/CHANGE_LOG/change-log.2.0.0.md__;!!OSsGDw!d_dJlNtYLmD585It0DKukzB2TS5KZqBZQ-pdI1D-6c6c5hRDotd6GyqYDgG_$ >";
    reference
      "ONF-TR-527, ONF-TR-512, ONF-TR-531, RFC 6020, RFC 6087 and ONF TAPI UML model
       <https://urldefense.com/v3/__https://github.com/OpenNetworkingFoundation/TAPI/tree/v2.0.0/UML__;!!OSsGDw!d_dJlNtYLmD585It0DKukzB2TS5KZqBZQ-pdI1D-6c6c5hRDotd6G1V9Thk9$ >";
  }

  typedef ncs_template_odu-type {
    type string;
    description
      "none";
  }

  typedef ncs_template_mapping-type {
    type string;
    description
      "none";
  }

  typedef ncs_template_tim-det-mo {
    type string;
    description
      "List of modes for trace identifier mismatch detection.";
  }

  typedef ncs_template_odu-slot-size {
    type string;
    description
      "none";
  }

  typedef ncs_template_odu-named-payload-type {
    type string;
    description
      "none";
  }

  typedef ncs_template_deg-thr-type {
    type string;
    description
      "The value of the threshold can be provisioned in terms of number of errored blocks or in terms of percentage of errored blocks. For percentage-based specification, in order to support provision of less than 1%, the specification consists of two fields. The first field indicates the granularity of percentage. For examples, in 1%, in 0.1%, or in 0.01%, etc. The second field indicates the multiple of the granularity. For number of errored block based, the value is a positive integer.";
  }

  typedef ncs_template_tcm-status {
    type string;
    description
      "See Table 15-5/G.709/Y.1331 ";
  }

  typedef ncs_template_tcm-mode {
    type string;
    description
      "List of value modes for the sink side of the tandem connection monitoring function.";
  }

  typedef ncs_template_tcm-monitoring {
    type string;
    description
      "Monitoring types for the tandem connection monitoring function.";
  }

  typedef ncs_template_tcm-extension {
    type string;
    description
      "none";
  }

  typedef ncs_template_percentage-granularity {
    type string;
    description
      "none";
  }

  typedef ncs_rpc_notif_odu-type {
    type identityref {
      base ODU_TYPE;
    }
    description
      "none";
  }

  typedef ncs_rpc_notif_mapping-type {
    type enumeration {
      enum "AMP" {
        description
          "none";
      }
      enum "BMP" {
        description
          "none";
      }
      enum "GFP-F" {
        description
          "none";
      }
      enum "GMP" {
        description
          "none";
      }
      enum "TTP_GFP_BMP" {
        description
          "none";
      }
      enum "NULL" {
        description
          "none";
      }
    }
    description
      "none";
  }

  typedef ncs_rpc_notif_tim-det-mo {
    type enumeration {
      enum "DAPI" {
        description
          "none";
      }
      enum "SAPI" {
        description
          "none";
      }
      enum "BOTH" {
        description
          "none";
      }
      enum "OFF" {
        description
          "none";
      }
    }
    description
      "List of modes for trace identifier mismatch detection.";
  }

  typedef ncs_rpc_notif_odu-slot-size {
    type enumeration {
      enum "1G25" {
        description
          "none";
      }
      enum "2G5" {
        description
          "none";
      }
    }
    description
      "none";
  }

  typedef ncs_rpc_notif_odu-named-payload-type {
    type enumeration {
      enum "UNKNOWN" {
        description
          "none";
      }
      enum "UNINTERPRETABLE" {
        description
          "none";
      }
    }
    description
      "none";
  }

  typedef ncs_rpc_notif_deg-thr-type {
    type enumeration {
      enum "PERCENTAGE" {
        description
          "Choice of % or Number of errored blocks";
      }
      enum "NUMBER_ERRORED_BLOCKS" {
        description
          "Number of % or blocks";
      }
    }
    description
      "The value of the threshold can be provisioned in terms of number of errored blocks or in terms of percentage of errored blocks. For percentage-based specification, in order to support provision of less than 1%, the specification consists of two fields. The first field indicates the granularity of percentage. For examples, in 1%, in 0.1%, or in 0.01%, etc. The second field indicates the multiple of the granularity. For number of errored block based, the value is a positive integer.";
  }

  typedef ncs_rpc_notif_tcm-status {
    type enumeration {
      enum "NO_SOURCE_TC" {
        description
          "TCM byte 3 (bits 6 7 8) -- 0 0 0, No source Tandem Connection";
      }
      enum "IN_USE_WITHOUT_IAE" {
        description
          "TCM byte 3 (bits 6 7 8) -- 0 0 1,  In use without IAE (Incoming Alignment Error)";
      }
      enum "IN_USE_WITH_IAE" {
        description
          "TCM byte 3 (bits 6 7 8) -- 0 1 0, In use with IAE (Incoming Alignment Error)";
      }
      enum "RESERVED_1" {
        description
          "TCM byte 3 (bits 6 7 8) -- 0 1 1, Reserved for future international standardization";
      }
      enum "RESERVED_2" {
        description
          "TCM byte 3 (bits 6 7 8) -- 1 0 0, Reserved for future international standardization";
      }
      enum "LCK" {
        description
          "TCM byte 3 (bits 6 7 8) -- 1 0 1, Maintenance signal: ODU-LCK";
      }
      enum "OCI" {
        description
          "TCM byte 3 (bits 6 7 8) -- 1 1 0, Maintenance signal: ODU-OCI";
      }
      enum "AIS" {
        description
          "TCM byte 3 (bits 6 7 8) -- 1 1 1, Maintenance signal: ODU-AIS";
      }
    }
    description
      "See Table 15-5/G.709/Y.1331 ";
  }

  typedef ncs_rpc_notif_tcm-mode {
    type enumeration {
      enum "OPERATIONAL" {
        description
          "none";
      }
      enum "TRANSPARENT" {
        description
          "none";
      }
      enum "MONITOR" {
        description
          "none";
      }
    }
    description
      "List of value modes for the sink side of the tandem connection monitoring function.";
  }

  typedef ncs_rpc_notif_tcm-monitoring {
    type enumeration {
      enum "INTRUSIVE" {
        description
          "none";
      }
      enum "NON-INTRUSIVE" {
        description
          "none";
      }
    }
    description
      "Monitoring types for the tandem connection monitoring function.";
  }

  typedef ncs_rpc_notif_tcm-extension {
    type enumeration {
      enum "NORMAL" {
        description
          "none";
      }
      enum "PASS-THROUGH" {
        description
          "none";
      }
      enum "ERASE" {
        description
          "none";
      }
    }
    description
      "none";
  }

  typedef ncs_rpc_notif_percentage-granularity {
    type enumeration {
      enum "ONES" {
        description
          "none";
      }
      enum "ONE_TENTHS" {
        description
          "value * (1/10)";
      }
      enum "ONE_HUNDREDTHS" {
        description
          "value * (1/100)";
      }
      enum "ONE_THOUSANDTHS" {
        description
          "value * (1/1000)";
      }
    }
    description
      "none";
  }

  typedef live_ncs_odu-type {
    type identityref {
      base ODU_TYPE;
    }
    description
      "none";
  }

  typedef live_ncs_mapping-type {
    type enumeration {
      enum "AMP" {
        description
          "none";
      }
      enum "BMP" {
        description
          "none";
      }
      enum "GFP-F" {
        description
          "none";
      }
      enum "GMP" {
        description
          "none";
      }
      enum "TTP_GFP_BMP" {
        description
          "none";
      }
      enum "NULL" {
        description
          "none";
      }
    }
    description
      "none";
  }

  typedef live_ncs_tim-det-mo {
    type enumeration {
      enum "DAPI" {
        description
          "none";
      }
      enum "SAPI" {
        description
          "none";
      }
      enum "BOTH" {
        description
          "none";
      }
      enum "OFF" {
        description
          "none";
      }
    }
    description
      "List of modes for trace identifier mismatch detection.";
  }

  typedef live_ncs_odu-slot-size {
    type enumeration {
      enum "1G25" {
        description
          "none";
      }
      enum "2G5" {
        description
          "none";
      }
    }
    description
      "none";
  }

  typedef live_ncs_odu-named-payload-type {
    type enumeration {
      enum "UNKNOWN" {
        description
          "none";
      }
      enum "UNINTERPRETABLE" {
        description
          "none";
      }
    }
    description
      "none";
  }

  typedef live_ncs_deg-thr-type {
    type enumeration {
      enum "PERCENTAGE" {
        description
          "Choice of % or Number of errored blocks";
      }
      enum "NUMBER_ERRORED_BLOCKS" {
        description
          "Number of % or blocks";
      }
    }
    description
      "The value of the threshold can be provisioned in terms of number of errored blocks or in terms of percentage of errored blocks. For percentage-based specification, in order to support provision of less than 1%, the specification consists of two fields. The first field indicates the granularity of percentage. For examples, in 1%, in 0.1%, or in 0.01%, etc. The second field indicates the multiple of the granularity. For number of errored block based, the value is a positive integer.";
  }

  typedef live_ncs_tcm-status {
    type enumeration {
      enum "NO_SOURCE_TC" {
        description
          "TCM byte 3 (bits 6 7 8) -- 0 0 0, No source Tandem Connection";
      }
      enum "IN_USE_WITHOUT_IAE" {
        description
          "TCM byte 3 (bits 6 7 8) -- 0 0 1,  In use without IAE (Incoming Alignment Error)";
      }
      enum "IN_USE_WITH_IAE" {
        description
          "TCM byte 3 (bits 6 7 8) -- 0 1 0, In use with IAE (Incoming Alignment Error)";
      }
      enum "RESERVED_1" {
        description
          "TCM byte 3 (bits 6 7 8) -- 0 1 1, Reserved for future international standardization";
      }
      enum "RESERVED_2" {
        description
          "TCM byte 3 (bits 6 7 8) -- 1 0 0, Reserved for future international standardization";
      }
      enum "LCK" {
        description
          "TCM byte 3 (bits 6 7 8) -- 1 0 1, Maintenance signal: ODU-LCK";
      }
      enum "OCI" {
        description
          "TCM byte 3 (bits 6 7 8) -- 1 1 0, Maintenance signal: ODU-OCI";
      }
      enum "AIS" {
        description
          "TCM byte 3 (bits 6 7 8) -- 1 1 1, Maintenance signal: ODU-AIS";
      }
    }
    description
      "See Table 15-5/G.709/Y.1331 ";
  }

  typedef live_ncs_tcm-mode {
    type enumeration {
      enum "OPERATIONAL" {
        description
          "none";
      }
      enum "TRANSPARENT" {
        description
          "none";
      }
      enum "MONITOR" {
        description
          "none";
      }
    }
    description
      "List of value modes for the sink side of the tandem connection monitoring function.";
  }

  typedef live_ncs_tcm-monitoring {
    type enumeration {
      enum "INTRUSIVE" {
        description
          "none";
      }
      enum "NON-INTRUSIVE" {
        description
          "none";
      }
    }
    description
      "Monitoring types for the tandem connection monitoring function.";
  }

  typedef live_ncs_tcm-extension {
    type enumeration {
      enum "NORMAL" {
        description
          "none";
      }
      enum "PASS-THROUGH" {
        description
          "none";
      }
      enum "ERASE" {
        description
          "none";
      }
    }
    description
      "none";
  }

  typedef live_ncs_percentage-granularity {
    type enumeration {
      enum "ONES" {
        description
          "none";
      }
      enum "ONE_TENTHS" {
        description
          "value * (1/10)";
      }
      enum "ONE_HUNDREDTHS" {
        description
          "value * (1/100)";
      }
      enum "ONE_THOUSANDTHS" {
        description
          "value * (1/1000)";
      }
    }
    description
      "none";
  }

  typedef odu-type {
    type identityref {
      base ODU_TYPE;
    }
    description
      "none";
  }

  typedef mapping-type {
    type enumeration {
      enum "AMP" {
        description
          "none";
      }
      enum "BMP" {
        description
          "none";
      }
      enum "GFP-F" {
        description
          "none";
      }
      enum "GMP" {
        description
          "none";
      }
      enum "TTP_GFP_BMP" {
        description
          "none";
      }
      enum "NULL" {
        description
          "none";
      }
    }
    description
      "none";
  }

  typedef tim-det-mo {
    type enumeration {
      enum "DAPI" {
        description
          "none";
      }
      enum "SAPI" {
        description
          "none";
      }
      enum "BOTH" {
        description
          "none";
      }
      enum "OFF" {
        description
          "none";
      }
    }
    description
      "List of modes for trace identifier mismatch detection.";
  }

  typedef odu-slot-size {
    type enumeration {
      enum "1G25" {
        description
          "none";
      }
      enum "2G5" {
        description
          "none";
      }
    }
    description
      "none";
  }

  typedef odu-named-payload-type {
    type enumeration {
      enum "UNKNOWN" {
        description
          "none";
      }
      enum "UNINTERPRETABLE" {
        description
          "none";
      }
    }
    description
      "none";
  }

  typedef deg-thr-type {
    type enumeration {
      enum "PERCENTAGE" {
        description
          "Choice of % or Number of errored blocks";
      }
      enum "NUMBER_ERRORED_BLOCKS" {
        description
          "Number of % or blocks";
      }
    }
    description
      "The value of the threshold can be provisioned in terms of number of errored blocks or in terms of percentage of errored blocks. For percentage-based specification, in order to support provision of less than 1%, the specification consists of two fields. The first field indicates the granularity of percentage. For examples, in 1%, in 0.1%, or in 0.01%, etc. The second field indicates the multiple of the granularity. For number of errored block based, the value is a positive integer.";
  }

  typedef tcm-status {
    type enumeration {
      enum "NO_SOURCE_TC" {
        description
          "TCM byte 3 (bits 6 7 8) -- 0 0 0, No source Tandem Connection";
      }
      enum "IN_USE_WITHOUT_IAE" {
        description
          "TCM byte 3 (bits 6 7 8) -- 0 0 1,  In use without IAE (Incoming Alignment Error)";
      }
      enum "IN_USE_WITH_IAE" {
        description
          "TCM byte 3 (bits 6 7 8) -- 0 1 0, In use with IAE (Incoming Alignment Error)";
      }
      enum "RESERVED_1" {
        description
          "TCM byte 3 (bits 6 7 8) -- 0 1 1, Reserved for future international standardization";
      }
      enum "RESERVED_2" {
        description
          "TCM byte 3 (bits 6 7 8) -- 1 0 0, Reserved for future international standardization";
      }
      enum "LCK" {
        description
          "TCM byte 3 (bits 6 7 8) -- 1 0 1, Maintenance signal: ODU-LCK";
      }
      enum "OCI" {
        description
          "TCM byte 3 (bits 6 7 8) -- 1 1 0, Maintenance signal: ODU-OCI";
      }
      enum "AIS" {
        description
          "TCM byte 3 (bits 6 7 8) -- 1 1 1, Maintenance signal: ODU-AIS";
      }
    }
    description
      "See Table 15-5/G.709/Y.1331 ";
  }

  typedef tcm-mode {
    type enumeration {
      enum "OPERATIONAL" {
        description
          "none";
      }
      enum "TRANSPARENT" {
        description
          "none";
      }
      enum "MONITOR" {
        description
          "none";
      }
    }
    description
      "List of value modes for the sink side of the tandem connection monitoring function.";
  }

  typedef tcm-monitoring {
    type enumeration {
      enum "INTRUSIVE" {
        description
          "none";
      }
      enum "NON-INTRUSIVE" {
        description
          "none";
      }
    }
    description
      "Monitoring types for the tandem connection monitoring function.";
  }

  typedef tcm-extension {
    type enumeration {
      enum "NORMAL" {
        description
          "none";
      }
      enum "PASS-THROUGH" {
        description
          "none";
      }
      enum "ERASE" {
        description
          "none";
      }
    }
    description
      "none";
  }

  typedef percentage-granularity {
    type enumeration {
      enum "ONES" {
        description
          "none";
      }
      enum "ONE_TENTHS" {
        description
          "value * (1/10)";
      }
      enum "ONE_HUNDREDTHS" {
        description
          "value * (1/100)";
      }
      enum "ONE_THOUSANDTHS" {
        description
          "value * (1/1000)";
      }
    }
    description
      "none";
  }

  grouping ncs_template_odu-termination-and-client-adaptation-pac {
    // NCS drop config false leaf 'opu-tributary-slot-size'
    // NCS drop config false leaf 'auto-payload-type'
    // NCS drop config false leaf 'configured-client-type'
    // NCS drop config false leaf 'configured-mapping-type'
    // NCS drop config false container 'accepted-payload-type'
    // NCS drop config false container 'fec-parameters'
    leaf-list odu-cn-effective-time-slot-list {
      // NCS patched for predictable order
      ordered-by user;
      type string;
      description
        "This attribute contains a set of distinct (i.e. unique) integers (e.g. 2, 3, 5, 9, 15, 34 representing the tributary slots TS#1.2, TS#1.3, TS#1.5, TS#1.9, TS#1.15, and TS#2.14)
         which represents the list of effective time slots which are available for carrying ODUk clients.
         Each entry in the list is an integer value (P) representing the time slot name TS#A.B (see ITU-T Recommendation G.709 (v5) Clause 20.1).
         The mapping between P and A & B is: A = [P/20] + 1; B = P - (P/20]*20; where the sqaure bracket represents the whole integer.";
    }
    description
      "This Pac contains the attributes associated with the client adaptation function of the server layer TTP
       It is present only if the CEP contains a TTP";
  }

  grouping ncs_template_odu-connection-end-point-spec {
    container odu-common {
      uses ncs_template_odu-common-pac;
      description
        "none";
    }
    // NCS drop config false container 'odu-term-and-adapter'
    // NCS drop config false container 'odu-ctp'
    // NCS drop config false container 'odu-protection'
    description
      "none";
  }

  grouping ncs_template_odu-pool-pac {
    leaf client-capacity {
      type string;
      description
        "none";
    }
    // NCS drop config false leaf 'max-client-instances'
    // NCS drop config false leaf 'max-client-size'
    description
      "none";
  }

  grouping ncs_template_odu-node-edge-point-spec {
    // NCS drop config false container 'odu-pool'
    description
      "none";
  }

  grouping ncs_template_odu-ctp-pac {
    // NCS drop config false leaf-list 'tributary-slot-list'
    // NCS drop config false leaf 'tributary-port-number'
    // NCS drop config false leaf 'accepted-msi'
    description
      "This Pac contains the attributes associated with the CTP
       It is present only if the CEP contains a CTP";
  }

  grouping ncs_template_odu-mep-spec {
    container odu-mep {
      uses ncs_template_odu-mep-pac;
      description
        "none";
    }
    // NCS drop config false container 'odu-ncm'
    // NCS drop config false container 'odu-tcm'
    container odu-defect {
      uses ncs_template_odu-defect-pac;
      description
        "none";
    }
    container odu-pm {
      uses ncs_template_odu-pm-pac;
      description
        "none";
    }
    description
      "none";
  }

  grouping ncs_template_odu-protection-pac {
    leaf aps-enable {
      type string;
      // NCS drop default statement
      description
        "This attribute is for enabling/disabling the automatic protection switching (APS) capability at the transport adaptation function that is represented by the ODU_ConnectionTerminationPoint object class. It triggers the MI_APS_EN signal to the transport adaptation function.";
    }
    leaf aps-level {
      type string;
      description
        "This attribute is for configuring the automatic protection switching (APS) level that should operate at the transport adaptation function that is represented by the ODU_ConnectionTerminationPoint object class. It triggers the MI_APS_LVL signal to the transport adaptation function. The value 0 means path and the values 1 through 6 mean TCM level 1 through 6 respectively.";
    }
    description
      "none";
  }

  grouping ncs_template_odu-ncm-pac {
    // NCS drop config false leaf-list 'tcm-fields-in-use'
    description
      "none";
  }

  grouping ncs_template_odu-tcm-mep-pac {
    leaf tcm-extension {
      type ncs_template_tcm-extension;
      description
        "none";
    }
    leaf tcm-mode {
      type ncs_template_tcm-mode;
      description
        "This attribute specifies the TCM mode at the entity. Valid values are: Operational, Monitor, and Transparent.";
    }
    // NCS drop config false leaf codirectional
    // NCS drop config false leaf 'ac-status-source'
    // NCS drop config false leaf 'ac-status-sink'
    leaf admin-state-source {
      type tapi-common:ncs_template_administrative-state;
      description
        "This attribute provides the capability to provision the LOCK signal at the source, which is one of the ODU maintenance signals.  When a Tandem Connection endpoint is set to admin state locked, it will insert the ODU-LCK signal in the source direction.";
    }
    leaf admin-state-sink {
      type tapi-common:ncs_template_administrative-state;
      description
        "This attribute provides the capability to provision the LOCK signal at the sink, which is one of the ODU maintenance signals. When a Tandem Connection endpoint is set to admin state locked, it will insert the ODU-LCK signal in the downstream direction.";
    }
    uses ncs_template_odu-tcm-mip-pac;
    description
      "none";
  }

  grouping ncs_template_odu-mip-spec {
    // NCS drop config false container 'odu-mip'
    // NCS drop config false container 'odu-ncm'
    // NCS drop config false container 'odu-tcm'
    container odu-pm {
      uses ncs_template_odu-pm-pac;
      description
        "none";
    }
    container odu-defect {
      uses ncs_template_odu-defect-pac;
      description
        "none";
    }
    description
      "none";
  }

  grouping ncs_template_odu-mip-pac {
    // NCS drop config false leaf acti
    leaf ex-dapi {
      type string;
      description
        "The Expected Destination Access Point Identifier (ExDAPI), provisioned by the managing system, to be compared with the TTI accepted at the overhead position of the sink for the purpose of checking the integrity of connectivity.";
    }
    leaf ex-sapi {
      type string;
      description
        "The Expected Source Access Point Identifier (ExSAPI), provisioned by the managing system, to be compared with the TTI accepted at the overhead position of the sink for the purpose of checking the integrity of connectivity.
        ";
    }
    leaf tim-act-disabled {
      type string;
      // NCS drop default statement
      description
        "This attribute provides the control capability for the managing system to enable or disable the Consequent Action function when detecting Trace Identifier Mismatch (TIM) at the trail termination sink.";
    }
    leaf tim-det-mode {
      type ncs_template_tim-det-mo;
      description
        "This attribute indicates the mode of the Trace Identifier Mismatch (TIM) Detection function allowed values: OFF, SAPIonly, DAPIonly, SAPIandDAPI";
    }
    leaf deg-m {
      type string;
      description
        "This attribute indicates the threshold level for declaring a Degraded Signal defect (dDEG). A dDEG shall be declared if DegM consecutive bad PM Seconds are detected.";
    }
    container deg-thr {
      uses ncs_template_deg-thr;
      description
        "This attribute indicates the threshold level for declaring a performance monitoring (PM) Second to be bad. The value of the threshold can be provisioned in terms of number of errored blocks or in terms of percentage of errored blocks. For percentage-based specification, in order to support provision of less than 1%, the specification consists of two fields. The first field indicates the granularity of percentage. For examples, in 1%, in 0.1%, or in 0.01%, etc. The second field indicates the multiple of the granularity. For number of errored block based, the value is a positive integer.";
    }
    description
      "none";
  }

  grouping ncs_template_odu-tcm-mip-pac {
    // NCS drop config false leaf 'tcm-field'
    description
      "none";
  }

  grouping ncs_template_odu-mep-pac {
    leaf dm-source {
      type string;
      description
        "This attribute is for configuring the delay measurement process at the trail termination function represented by the subject TTP object class. It models the MI_DM_Source MI signal. If MI_DM_Source is false, then the value of the DMp bit is determined by the RI_DM. If MI_DM_Source is true, then the value of the DMp bit is set to MI_DMValue.";
    }
    leaf dm-value {
      type string;
      description
        "This attribute is for setting the DMp and DMti bits of the delay measurement process. The value of 'true' sets the DMp and DMti bits to 0 and the value of 'false' to 1.";
    }
    leaf txti {
      type string;
      description
        "The Trail Trace Identifier (TTI) information, provisioned by the managing system at the termination source, to be placed in the TTI overhead position of the source of a trail for transmission.
        ";
    }
    uses ncs_template_odu-mip-pac;
    description
      "none";
  }

  grouping ncs_template_odu-common-pac {
    // NCS drop config false leaf 'odu-type'
    // NCS drop config false leaf 'odu-rate'
    // NCS drop config false leaf 'odu-rate-tolerance'
    leaf number-of-odu-c {
      type string;
      // NCS drop default statement
      description
        "This attribute specifies the number of ODUC instances of the ODUCn.";
    }
    description
      "none";
  }

  grouping ncs_template_odu-pm-pac {
    leaf n-bbe {
      type string;
      description
        "Near-end Background Block Error";
    }
    // NCS drop config false leaf 'f-bbe'
    leaf n-ses {
      type string;
      description
        "Near-end Severely Errored Second";
    }
    leaf f-ses {
      type string;
      description
        "Far-end Severely Errored Second";
    }
    container uas {
      uses ncs_template_uas-choice;
      description
        "UnAvailable Second";
    }
    description
      "Instance of this object class contains the ODUP layer-specific Current Data. This object class is a subclass of the OTN_CurrentData object class.
       PM data attributes: fBbe, fSes, nBbe, nSes. uas";
  }

  grouping ncs_template_odu-defect-pac {
    // NCS drop config false leaf bdi
    // NCS drop config false leaf deg
    // NCS drop config false leaf lck
    // NCS drop config false leaf oci
    // NCS drop config false leaf ssf
    // NCS drop config false leaf tim
    description
      "The valid list of defects raised on the entity. If the value of any attribute is true, then the corresponding defect is raised.";
  }

  grouping ncs_template_odu-connectivity-service-end-point-spec {
    container odu-csep-ctp-pac {
      uses ncs_template_odu-csep-ctp-pac;
      description
        "none";
    }
    container odu-csep-ttp-pac {
      uses ncs_template_odu-csep-ttp-pac;
      description
        "none";
    }
    container odu-csep-common-pac {
      uses ncs_template_odu-csep-common-pac;
      description
        "none";
    }
    description
      "none";
  }

  grouping ncs_template_odu-csep-ctp-pac {
    leaf tributary-port-number {
      type string;
      description
        "This attribute identifies the tributary port number that is associated with the ODUk CTP. This attribute applies when the ODUk CTP is multiplexed into a server layer ODU TTP object.
         It will not apply if this ODUk CTP object is directly mapped into an OTUk TTP object (i.e. OTUk has no tributary slots).
         The upper bound of the integer allowed in this set is a function of the ODU server layer into which the ODUk CTP is multiplexed.
         In case the ODU server layer is an HO-ODUk, the upper bound is the maximum number of tributary slots within the HO-ODUk (see ITU-T Recommendation G.709 (v5) clause 19.4.1).
         Thus, for example, M=8/32/80 for ODU2/ODU3/ODU4 server layers (respectively) using 1.25G slot size.
         In case the ODU server layer is an ODUCn, the upper bound is M=10*n (see ITU-T Recommendation G.709 (v5) Clause 20.4.1).
         range of type : The value range depends on the size of the Tributary Port Number (TPN) field used which depends on th server-layer ODU or OTU.
         In case of ODUk mapping into OTUk, there is no TPN field, so the tributaryPortNumber shall be zero.
         In case of LO ODUj mapping over ODU1, ODU2 or ODU3, the TPN is encoded in a 6-bit field so the value range is 0-63. See clause 14.4.1/G.709-2016.
         In case of LO ODUj mapping over ODU4, the TPN is encoded in a 7-bit field so the value range is 0-127. See clause 14.4.1.4/G.709-2016.
         In case of ODUk mapping over ODUCn, the TPN is encoded in a 14-bit field so the value range is 0-16383. See clause 20.4.1.1/G.709-2016.
        ";
    }
    leaf-list tributary-slot-list {
      // NCS patched for predictable order
      ordered-by user;
      type string;
      description
        "ITU-T G.875 (v5)
         This attribute contains a set of distinct (i.e. unique) integers (e.g. 2, 3, 5, 9, 15 representing the tributary slots TS#2, TS#3, TS#5, TS#9 and TS#15) which represents the resources occupied by the ODUk CTP (e.g. an ODUflex with a bit rate of 6.25G setup over an HO-ODUk).
         This attribute applies when the ODUk CTP is carried by a sever layer ODU TTP object. It will not apply if this ODUk CTP object is directly carried by an OTUk TTP object (i.e. OTUk has no tributary slots).
         The upper bound of the integer allowed in this set and its relationship with the tributary slots are a function of the ODU server layer to which the ODUk CTP is carried over.
         In case the ODU server layer is an HO-ODUk, each entry in the list is an integer value (i) representing the tributary slot name TS#i and the upper bound is the maximum number of tributary slots within the HO-ODUk (see ITU-T Recommendation G.709 (v5) clause 19).
         Thus, for example, M=8/32/80 for ODU2/ODU3/ODU4 server layers (respectively) using 1.25G slot size.
         In case the ODU server layer is an ODUCn, each entry in the list is an integer value (P) representing the time slot name TS#A.B (e.g. 2, 3, 5, 9, 15, 34 representing the tributary slots TS#1.2, TS#1.3, TS#1.5, TS#1.9, TS#1.15, and TS#2.14) and the upper und is 20*n (see ITU-T Recommendation G.709 (v5) Clause 20.1).
         The mapping between P and A & B is: A = [P/20] + 1; B = P - (P/20]*20; where the square bracket represents the whole integer. Note that the value of this attribute can be changed only in the case of ODUflex and has to be through specific operations (i.e. not be changing the attribute tributarySlotList directly).";
    }
    description
      "none";
  }

  grouping ncs_template_odu-csep-ttp-pac {
    leaf configured-mapping-type {
      type ncs_template_mapping-type;
      description
        "This attributes indicates the configured mapping type.";
    }
    // NCS drop config false leaf 'configured-client-type'
    description
      "none";
  }

  grouping ncs_template_odu-csep-common-pac {
    leaf odu-type {
      type ncs_template_odu-type;
      description
        "This attribute specifies the type of the ODU termination point.";
    }
    leaf odu-rate {
      type string;
      description
        "This attribute indicates the rate of the ODU termination point in Kbits/s.
         This attribute is Set at create; i.e., once created it cannot be changed directly.
         In case of resizable ODU flex, its value can be changed via HAO (not directly on the attribute).
         This attribute indicates the rate of the ODU termination point.
         Valid values shall be consistent with the oduType configuration as shown in Table 7-2/G.709 v5.
         Setting this value for fixed-rate ODUk types (e.g., ODU0), is optional.
         The default value is derived from the configured oduType, as defined in Table 7-2/G.709 v5.
         Setting this value for ODUCn type is optional. The default value is derived from the configured n of the ODUCn as defined in Table 7-2/G.709 v5.";
    }
    leaf opu-tributary-slot-size {
      type ncs_template_odu-slot-size;
      description
        "This attribute is applicable for ODU2 and ODU3 CTP only. It indicates the slot size of the ODU CTP.";
    }
    leaf number-of-odu-c {
      type string;
      // NCS drop default statement
      description
        "This attribute specifies the number of ODUC instances of the ODUCn.";
    }
    description
      "none";
  }

  grouping ncs_template_odu-payload-type {
    leaf named-payload-type {
      type ncs_template_odu-named-payload-type;
      description
        "none";
    }
    leaf hex-payload-type {
      type string;
      description
        "none";
    }
    description
      "none";
  }

  grouping ncs_template_deg-thr {
    leaf deg-thr-value {
      type string;
      description
        "Percentage of detected errored blocks";
    }
    leaf deg-thr-type {
      type ncs_template_deg-thr-type;
      description
        "Number of errored blocks";
    }
    leaf percentage-granularity {
      type ncs_template_percentage-granularity;
      description
        "none";
    }
    description
      "Degraded Threshold, specify either the percentage or the number of Errored Blocks in the defined interval.
       degThrValue when type is PERCENTAGE:
       percentageGranularity is used to indicate the number of decimal points
       So if percentageGranularity is ones, a value of 1 in degThrValue would indicate 1%, a value of 10 = 10%, a value of 100 = 100%
       So if percentageGranularity is thousandths a value of 1 in degThrValue would indicate 0.001%, a value of 1000 = 1%, a value of 1000000 = 100%
       degThrValue when type is NUMBER_ERROR_BLOCKS:
       Number of Errored Blocks is captured in an integer value.";
  }

  grouping ncs_template_uas-choice {
    leaf bidirectional {
      type string;
      // NCS drop default statement
      description
        "none";
    }
    leaf uas {
      type string;
      description
        "none";
    }
    leaf nuas {
      type string;
      description
        "none";
    }
    leaf fuas {
      type string;
      description
        "none";
    }
    description
      "If bidirectional is TRUE then use the uas attribute, if bidirectional is FALSE use the nuas, and fuas attributes";
  }

  grouping ncs_template_fec-properties {
    leaf pre-fec-ber {
      type string;
      description
        "counter: bit error rate before correction by FEC";
    }
    leaf post-fec-ber {
      type string;
      description
        "counter: bit error rate after correction by FEC";
    }
    leaf corrected-bytes {
      type string;
      description
        "Bytes corrected between those that were received corrupted";
    }
    leaf corrected-bits {
      type string;
      description
        "Bits corrected between those that were received corrupted";
    }
    leaf uncorrectable-bytes {
      type string;
      description
        "Bytes that could not be corrected by FEC";
    }
    leaf uncorrectable-bits {
      type string;
      description
        "Bits that could not be corrected by FEC";
    }
    description
      "none";
  }

  grouping ncs_rpc_notif_odu-termination-and-client-adaptation-pac {
    leaf opu-tributary-slot-size {
      type ncs_rpc_notif_odu-slot-size;
      config false;
      description
        "This attribute is applicable for ODU2 and ODU3 CTP only. It indicates the slot size of the ODU CTP.";
    }
    leaf auto-payload-type {
      type boolean;
      config false;
      description
        "This attribute is applicable when the ODU CTP object instance represents a lower order ODU CTP Source at the client layer of the ODUP/ODUj-21 adaptation function. The value of true of this attribute configures that the adaptation source function shall fall back to the payload type PT=20 if the conditions specified in 14.3.10.1/G.798 are satisfied. ";
    }
    leaf configured-client-type {
      type tapi-dsr:ncs_rpc_notif_digital-signal-type;
      config false;
      description
        "This attribute configures the type of the client CTP of the server ODU TTP.";
    }
    leaf configured-mapping-type {
      type ncs_rpc_notif_mapping-type;
      config false;
      description
        "This attributes indicates the configured mapping type.";
    }
    container accepted-payload-type {
      config false;
      uses ncs_rpc_notif_odu-payload-type;
      description
        "This attribute is applicable when the ODU CTP object instance represents a lower order ODU CTP Sink at the client layer of the ODUP/ODU[i]j or ODUP/ODUj-21 adaptation function.
         This attribute is a 2-digit Hex code that indicates the new accepted payload type.
         Valid values are defined in Table 15-8 of ITU-T Recommendation G.709 with one additional value UN_INTERPRETABLE.";
    }
    container fec-parameters {
      config false;
      uses ncs_rpc_notif_fec-properties;
      description
        "none";
    }
    leaf-list odu-cn-effective-time-slot-list {
      type uint64;
      description
        "This attribute contains a set of distinct (i.e. unique) integers (e.g. 2, 3, 5, 9, 15, 34 representing the tributary slots TS#1.2, TS#1.3, TS#1.5, TS#1.9, TS#1.15, and TS#2.14)
         which represents the list of effective time slots which are available for carrying ODUk clients.
         Each entry in the list is an integer value (P) representing the time slot name TS#A.B (see ITU-T Recommendation G.709 (v5) Clause 20.1).
         The mapping between P and A & B is: A = [P/20] + 1; B = P - (P/20]*20; where the sqaure bracket represents the whole integer.";
    }
    description
      "This Pac contains the attributes associated with the client adaptation function of the server layer TTP
       It is present only if the CEP contains a TTP";
  }

  grouping ncs_rpc_notif_odu-connection-end-point-spec {
    container odu-common {
      uses ncs_rpc_notif_odu-common-pac;
      description
        "none";
    }
    container odu-term-and-adapter {
      config false;
      uses ncs_rpc_notif_odu-termination-and-client-adaptation-pac;
      description
        "none";
    }
    container odu-ctp {
      config false;
      uses ncs_rpc_notif_odu-ctp-pac;
      description
        "none";
    }
    container odu-protection {
      config false;
      uses ncs_rpc_notif_odu-protection-pac;
      description
        "none";
    }
    description
      "none";
  }

  grouping ncs_rpc_notif_odu-pool-pac {
    leaf client-capacity {
      type uint64;
      description
        "none";
    }
    leaf max-client-instances {
      type uint64;
      config false;
      description
        "none";
    }
    leaf max-client-size {
      type uint64;
      config false;
      description
        "none";
    }
    description
      "none";
  }

  grouping ncs_rpc_notif_odu-node-edge-point-spec {
    container odu-pool {
      config false;
      uses ncs_rpc_notif_odu-pool-pac;
      description
        "none";
    }
    description
      "none";
  }

  grouping ncs_rpc_notif_odu-ctp-pac {
    leaf-list tributary-slot-list {
      type uint64;
      config false;
      description
        "ITU-T G.875 (v5)
         This attribute contains a set of distinct (i.e. unique) integers (e.g. 2, 3, 5, 9, 15 representing the tributary slots TS#2, TS#3, TS#5, TS#9 and TS#15) which represents the resources occupied by the ODUk CTP (e.g. an ODUflex with a bit rate of 6.25G setup over an HO-ODUk).
         This attribute applies when the ODUk CTP is carried by a sever layer ODU TTP object. It will not apply if this ODUk CTP object is directly carried by an OTUk TTP object (i.e. OTUk has no tributary slots).
         The upper bound of the integer allowed in this set and its relationship with the tributary slots are a function of the ODU server layer to which the ODUk CTP is carried over.
         In case the ODU server layer is an HO-ODUk, each entry in the list is an integer value (i) representing the tributary slot name TS#i and the upper bound is the maximum number of tributary slots within the HO-ODUk (see ITU-T Recommendation G.709 (v5) clause 19).
         Thus, for example, M=8/32/80 for ODU2/ODU3/ODU4 server layers (respectively) using 1.25G slot size.
         In case the ODU server layer is an ODUCn, each entry in the list is an integer value (P) representing the time slot name TS#A.B (e.g. 2, 3, 5, 9, 15, 34 representing the tributary slots TS#1.2, TS#1.3, TS#1.5, TS#1.9, TS#1.15, and TS#2.14) and the upper und is 20*n (see ITU-T Recommendation G.709 (v5) Clause 20.1).
         The mapping between P and A & B is: A = [P/20] + 1; B = P - (P/20]*20; where the square bracket represents the whole integer. Note that the value of this attribute can be changed only in the case of ODUflex and has to be through specific operations (i.e. not be changing the attribute tributarySlotList directly).";
    }
    leaf tributary-port-number {
      type uint64;
      config false;
      description
        "This attribute identifies the tributary port number that is associated with the ODUk CTP. This attribute applies when the ODUk CTP is multiplexed into a server layer ODU TTP object.
         It will not apply if this ODUk CTP object is directly mapped into an OTUk TTP object (i.e. OTUk has no tributary slots).
         The upper bound of the integer allowed in this set is a function of the ODU server layer into which the ODUk CTP is multiplexed.
         In case the ODU server layer is an HO-ODUk, the upper bound is the maximum number of tributary slots within the HO-ODUk (see ITU-T Recommendation G.709 (v5) clause 19.4.1).
         Thus, for example, M=8/32/80 for ODU2/ODU3/ODU4 server layers (respectively) using 1.25G slot size.
         In case the ODU server layer is an ODUCn, the upper bound is M=10*n (see ITU-T Recommendation G.709 (v5) Clause 20.4.1).
         range of type : The value range depends on the size of the Tributary Port Number (TPN) field used which depends on th server-layer ODU or OTU.
         In case of ODUk mapping into OTUk, there is no TPN field, so the tributaryPortNumber shall be zero.
         In case of LO ODUj mapping over ODU1, ODU2 or ODU3, the TPN is encoded in a 6-bit field so the value range is 0-63. See clause 14.4.1/G.709-2016.
         In case of LO ODUj mapping over ODU4, the TPN is encoded in a 7-bit field so the value range is 0-127. See clause 14.4.1.4/G.709-2016.
         In case of ODUk mapping over ODUCn, the TPN is encoded in a 14-bit field so the value range is 0-16383. See clause 20.4.1.1/G.709-2016.
        ";
    }
    leaf accepted-msi {
      type string;
      config false;
      description
        "This attribute is applicable when the ODU CTP object instance represents a lower order ODU1 or ODU2 CTP Sink at the client layer of the ODU3P/ODU12 adaptation function or represents a lower order ODUj CTP Sink at the client layer of the ODUP/ODUj-21 adaptation function. This attribute is a 1-byte field that represents the accepted multiplex structure of the adaptation function. ";
    }
    description
      "This Pac contains the attributes associated with the CTP
       It is present only if the CEP contains a CTP";
  }

  grouping ncs_rpc_notif_odu-mep-spec {
    container odu-mep {
      uses ncs_rpc_notif_odu-mep-pac;
      description
        "none";
    }
    container odu-ncm {
      config false;
      uses ncs_rpc_notif_odu-ncm-pac;
      description
        "none";
    }
    container odu-tcm {
      config false;
      uses ncs_rpc_notif_odu-tcm-mep-pac;
      description
        "none";
    }
    container odu-defect {
      uses ncs_rpc_notif_odu-defect-pac;
      description
        "none";
    }
    container odu-pm {
      uses ncs_rpc_notif_odu-pm-pac;
      description
        "none";
    }
    description
      "none";
  }

  grouping ncs_rpc_notif_odu-protection-pac {
    leaf aps-enable {
      type boolean;
      default "true";
      description
        "This attribute is for enabling/disabling the automatic protection switching (APS) capability at the transport adaptation function that is represented by the ODU_ConnectionTerminationPoint object class. It triggers the MI_APS_EN signal to the transport adaptation function.";
    }
    leaf aps-level {
      type uint64;
      description
        "This attribute is for configuring the automatic protection switching (APS) level that should operate at the transport adaptation function that is represented by the ODU_ConnectionTerminationPoint object class. It triggers the MI_APS_LVL signal to the transport adaptation function. The value 0 means path and the values 1 through 6 mean TCM level 1 through 6 respectively.";
    }
    description
      "none";
  }

  grouping ncs_rpc_notif_odu-ncm-pac {
    leaf-list tcm-fields-in-use {
      type uint64;
      config false;
      description
        "This attribute indicates the used TCM fields of the ODU OH.";
    }
    description
      "none";
  }

  grouping ncs_rpc_notif_odu-tcm-mep-pac {
    leaf tcm-extension {
      type ncs_rpc_notif_tcm-extension;
      description
        "none";
    }
    leaf tcm-mode {
      type ncs_rpc_notif_tcm-mode;
      description
        "This attribute specifies the TCM mode at the entity. Valid values are: Operational, Monitor, and Transparent.";
    }
    leaf codirectional {
      type boolean;
      config false;
      description
        "This attribute specifies the directionality of the ODUT MEP with respect to the associated ODU CEP. The value of TRUE means that the sink part of the ODUT MEP terminates the same signal direction as the sink part of the ODU CEP. The Source part behaves similarly. This attribute is meaningful only on objects instantiated under ODU CEP, and at least one among ODU CEP and the subordinate object is bidirectional.";
    }
    leaf ac-status-source {
      type ncs_rpc_notif_tcm-status;
      config false;
      description
        "This attribute indicates the status of the accepted TCM. ";
    }
    leaf ac-status-sink {
      type ncs_rpc_notif_tcm-status;
      config false;
      description
        "This attribute indicates the status of the accepted TCM. ";
    }
    leaf admin-state-source {
      type tapi-common:ncs_rpc_notif_administrative-state;
      description
        "This attribute provides the capability to provision the LOCK signal at the source, which is one of the ODU maintenance signals.  When a Tandem Connection endpoint is set to admin state locked, it will insert the ODU-LCK signal in the source direction.";
    }
    leaf admin-state-sink {
      type tapi-common:ncs_rpc_notif_administrative-state;
      description
        "This attribute provides the capability to provision the LOCK signal at the sink, which is one of the ODU maintenance signals. When a Tandem Connection endpoint is set to admin state locked, it will insert the ODU-LCK signal in the downstream direction.";
    }
    uses ncs_rpc_notif_odu-tcm-mip-pac;
    description
      "none";
  }

  grouping ncs_rpc_notif_odu-mip-spec {
    container odu-mip {
      config false;
      uses ncs_rpc_notif_odu-mip-pac;
      description
        "none";
    }
    container odu-ncm {
      config false;
      uses ncs_rpc_notif_odu-ncm-pac;
      description
        "none";
    }
    container odu-tcm {
      config false;
      uses ncs_rpc_notif_odu-tcm-mip-pac;
      description
        "none";
    }
    container odu-pm {
      uses ncs_rpc_notif_odu-pm-pac;
      description
        "none";
    }
    container odu-defect {
      uses ncs_rpc_notif_odu-defect-pac;
      description
        "none";
    }
    description
      "none";
  }

  grouping ncs_rpc_notif_odu-mip-pac {
    leaf acti {
      type string;
      config false;
      description
        "The Trail Trace Identifier (TTI) information recovered (Accepted) from the TTI overhead position at the sink of a trail.";
    }
    leaf ex-dapi {
      type string;
      description
        "The Expected Destination Access Point Identifier (ExDAPI), provisioned by the managing system, to be compared with the TTI accepted at the overhead position of the sink for the purpose of checking the integrity of connectivity.";
    }
    leaf ex-sapi {
      type string;
      description
        "The Expected Source Access Point Identifier (ExSAPI), provisioned by the managing system, to be compared with the TTI accepted at the overhead position of the sink for the purpose of checking the integrity of connectivity.
        ";
    }
    leaf tim-act-disabled {
      type boolean;
      default "true";
      description
        "This attribute provides the control capability for the managing system to enable or disable the Consequent Action function when detecting Trace Identifier Mismatch (TIM) at the trail termination sink.";
    }
    leaf tim-det-mode {
      type ncs_rpc_notif_tim-det-mo;
      description
        "This attribute indicates the mode of the Trace Identifier Mismatch (TIM) Detection function allowed values: OFF, SAPIonly, DAPIonly, SAPIandDAPI";
    }
    leaf deg-m {
      type uint64;
      description
        "This attribute indicates the threshold level for declaring a Degraded Signal defect (dDEG). A dDEG shall be declared if DegM consecutive bad PM Seconds are detected.";
    }
    container deg-thr {
      uses ncs_rpc_notif_deg-thr;
      description
        "This attribute indicates the threshold level for declaring a performance monitoring (PM) Second to be bad. The value of the threshold can be provisioned in terms of number of errored blocks or in terms of percentage of errored blocks. For percentage-based specification, in order to support provision of less than 1%, the specification consists of two fields. The first field indicates the granularity of percentage. For examples, in 1%, in 0.1%, or in 0.01%, etc. The second field indicates the multiple of the granularity. For number of errored block based, the value is a positive integer.";
    }
    description
      "none";
  }

  grouping ncs_rpc_notif_odu-tcm-mip-pac {
    leaf tcm-field {
      type uint64;
      config false;
      description
        "This attribute indicates the tandem connection monitoring field of the ODU OH.";
    }
    description
      "none";
  }

  grouping ncs_rpc_notif_odu-mep-pac {
    leaf dm-source {
      type boolean;
      description
        "This attribute is for configuring the delay measurement process at the trail termination function represented by the subject TTP object class. It models the MI_DM_Source MI signal. If MI_DM_Source is false, then the value of the DMp bit is determined by the RI_DM. If MI_DM_Source is true, then the value of the DMp bit is set to MI_DMValue.";
    }
    leaf dm-value {
      type boolean;
      description
        "This attribute is for setting the DMp and DMti bits of the delay measurement process. The value of 'true' sets the DMp and DMti bits to 0 and the value of 'false' to 1.";
    }
    leaf txti {
      type string;
      description
        "The Trail Trace Identifier (TTI) information, provisioned by the managing system at the termination source, to be placed in the TTI overhead position of the source of a trail for transmission.
        ";
    }
    uses ncs_rpc_notif_odu-mip-pac;
    description
      "none";
  }

  grouping ncs_rpc_notif_odu-common-pac {
    leaf odu-type {
      type ncs_rpc_notif_odu-type;
      config false;
      description
        "This attribute specifies the type of the ODU termination point.";
    }
    leaf odu-rate {
      type uint64;
      config false;
      description
        "This attribute indicates the rate of the ODU termination point in Kbits/s.
         This attribute is Set at create; i.e., once created it cannot be changed directly.
         In case of resizable ODU flex, its value can be changed via HAO (not directly on the attribute).
         This attribute indicates the rate of the ODU termination point.
         Valid values shall be consistent with the oduType configuration as shown in Table 7-2/G.709 v5.
         Setting this value for fixed-rate ODUk types (e.g., ODU0), is optional.
         The default value is derived from the configured oduType, as defined in Table 7-2/G.709 v5.
         Setting this value for ODUCn type is optional. The default value is derived from the configured n of the ODUCn as defined in Table 7-2/G.709 v5.";
    }
    leaf odu-rate-tolerance {
      type uint64;
      config false;
      description
        "This attribute indicates the rate tolerance of the ODU termination point.
         Valid values are real value in the unit of ppm.
         Standardized values are defined in Table 7-2/G.709.";
    }
    leaf number-of-odu-c {
      type uint64;
      default "1";
      description
        "This attribute specifies the number of ODUC instances of the ODUCn.";
    }
    description
      "none";
  }

  grouping ncs_rpc_notif_odu-pm-pac {
    leaf n-bbe {
      type uint64;
      description
        "Near-end Background Block Error";
    }
    leaf f-bbe {
      type uint64;
      config false;
      description
        "Far-end Background Block Error";
    }
    leaf n-ses {
      type uint64;
      description
        "Near-end Severely Errored Second";
    }
    leaf f-ses {
      type uint64;
      description
        "Far-end Severely Errored Second";
    }
    container uas {
      uses ncs_rpc_notif_uas-choice;
      description
        "UnAvailable Second";
    }
    description
      "Instance of this object class contains the ODUP layer-specific Current Data. This object class is a subclass of the OTN_CurrentData object class.
       PM data attributes: fBbe, fSes, nBbe, nSes. uas";
  }

  grouping ncs_rpc_notif_odu-defect-pac {
    leaf bdi {
      type boolean;
      config false;
      description
        "Backward Defect Indication";
    }
    leaf deg {
      type boolean;
      config false;
      description
        "Signal Degraded";
    }
    leaf lck {
      type boolean;
      config false;
      description
        "Locked";
    }
    leaf oci {
      type boolean;
      config false;
      description
        "Open Connection Indicator";
    }
    leaf ssf {
      type boolean;
      config false;
      description
        "Server Signal Failure";
    }
    leaf tim {
      type boolean;
      config false;
      description
        "Trail Trace Identifier Mismatch";
    }
    description
      "The valid list of defects raised on the entity. If the value of any attribute is true, then the corresponding defect is raised.";
  }

  grouping ncs_rpc_notif_odu-connectivity-service-end-point-spec {
    container odu-csep-ctp-pac {
      uses ncs_rpc_notif_odu-csep-ctp-pac;
      description
        "none";
    }
    container odu-csep-ttp-pac {
      uses ncs_rpc_notif_odu-csep-ttp-pac;
      description
        "none";
    }
    container odu-csep-common-pac {
      uses ncs_rpc_notif_odu-csep-common-pac;
      description
        "none";
    }
    description
      "none";
  }

  grouping ncs_rpc_notif_odu-csep-ctp-pac {
    leaf tributary-port-number {
      type uint64;
      description
        "This attribute identifies the tributary port number that is associated with the ODUk CTP. This attribute applies when the ODUk CTP is multiplexed into a server layer ODU TTP object.
         It will not apply if this ODUk CTP object is directly mapped into an OTUk TTP object (i.e. OTUk has no tributary slots).
         The upper bound of the integer allowed in this set is a function of the ODU server layer into which the ODUk CTP is multiplexed.
         In case the ODU server layer is an HO-ODUk, the upper bound is the maximum number of tributary slots within the HO-ODUk (see ITU-T Recommendation G.709 (v5) clause 19.4.1).
         Thus, for example, M=8/32/80 for ODU2/ODU3/ODU4 server layers (respectively) using 1.25G slot size.
         In case the ODU server layer is an ODUCn, the upper bound is M=10*n (see ITU-T Recommendation G.709 (v5) Clause 20.4.1).
         range of type : The value range depends on the size of the Tributary Port Number (TPN) field used which depends on th server-layer ODU or OTU.
         In case of ODUk mapping into OTUk, there is no TPN field, so the tributaryPortNumber shall be zero.
         In case of LO ODUj mapping over ODU1, ODU2 or ODU3, the TPN is encoded in a 6-bit field so the value range is 0-63. See clause 14.4.1/G.709-2016.
         In case of LO ODUj mapping over ODU4, the TPN is encoded in a 7-bit field so the value range is 0-127. See clause 14.4.1.4/G.709-2016.
         In case of ODUk mapping over ODUCn, the TPN is encoded in a 14-bit field so the value range is 0-16383. See clause 20.4.1.1/G.709-2016.
        ";
    }
    leaf-list tributary-slot-list {
      type uint64;
      description
        "ITU-T G.875 (v5)
         This attribute contains a set of distinct (i.e. unique) integers (e.g. 2, 3, 5, 9, 15 representing the tributary slots TS#2, TS#3, TS#5, TS#9 and TS#15) which represents the resources occupied by the ODUk CTP (e.g. an ODUflex with a bit rate of 6.25G setup over an HO-ODUk).
         This attribute applies when the ODUk CTP is carried by a sever layer ODU TTP object. It will not apply if this ODUk CTP object is directly carried by an OTUk TTP object (i.e. OTUk has no tributary slots).
         The upper bound of the integer allowed in this set and its relationship with the tributary slots are a function of the ODU server layer to which the ODUk CTP is carried over.
         In case the ODU server layer is an HO-ODUk, each entry in the list is an integer value (i) representing the tributary slot name TS#i and the upper bound is the maximum number of tributary slots within the HO-ODUk (see ITU-T Recommendation G.709 (v5) clause 19).
         Thus, for example, M=8/32/80 for ODU2/ODU3/ODU4 server layers (respectively) using 1.25G slot size.
         In case the ODU server layer is an ODUCn, each entry in the list is an integer value (P) representing the time slot name TS#A.B (e.g. 2, 3, 5, 9, 15, 34 representing the tributary slots TS#1.2, TS#1.3, TS#1.5, TS#1.9, TS#1.15, and TS#2.14) and the upper und is 20*n (see ITU-T Recommendation G.709 (v5) Clause 20.1).
         The mapping between P and A & B is: A = [P/20] + 1; B = P - (P/20]*20; where the square bracket represents the whole integer. Note that the value of this attribute can be changed only in the case of ODUflex and has to be through specific operations (i.e. not be changing the attribute tributarySlotList directly).";
    }
    description
      "none";
  }

  grouping ncs_rpc_notif_odu-csep-ttp-pac {
    leaf configured-mapping-type {
      type ncs_rpc_notif_mapping-type;
      description
        "This attributes indicates the configured mapping type.";
    }
    leaf configured-client-type {
      type tapi-dsr:ncs_rpc_notif_digital-signal-type;
      config false;
      description
        "This attribute configures the type of the client CTP of the server ODU TTP.";
    }
    description
      "none";
  }

  grouping ncs_rpc_notif_odu-csep-common-pac {
    leaf odu-type {
      type ncs_rpc_notif_odu-type;
      description
        "This attribute specifies the type of the ODU termination point.";
    }
    leaf odu-rate {
      type uint64;
      description
        "This attribute indicates the rate of the ODU termination point in Kbits/s.
         This attribute is Set at create; i.e., once created it cannot be changed directly.
         In case of resizable ODU flex, its value can be changed via HAO (not directly on the attribute).
         This attribute indicates the rate of the ODU termination point.
         Valid values shall be consistent with the oduType configuration as shown in Table 7-2/G.709 v5.
         Setting this value for fixed-rate ODUk types (e.g., ODU0), is optional.
         The default value is derived from the configured oduType, as defined in Table 7-2/G.709 v5.
         Setting this value for ODUCn type is optional. The default value is derived from the configured n of the ODUCn as defined in Table 7-2/G.709 v5.";
    }
    leaf opu-tributary-slot-size {
      type ncs_rpc_notif_odu-slot-size;
      description
        "This attribute is applicable for ODU2 and ODU3 CTP only. It indicates the slot size of the ODU CTP.";
    }
    leaf number-of-odu-c {
      type uint64;
      default "1";
      description
        "This attribute specifies the number of ODUC instances of the ODUCn.";
    }
    description
      "none";
  }

  grouping ncs_rpc_notif_odu-payload-type {
    leaf named-payload-type {
      type ncs_rpc_notif_odu-named-payload-type;
      description
        "none";
    }
    leaf hex-payload-type {
      type uint64;
      description
        "none";
    }
    description
      "none";
  }

  grouping ncs_rpc_notif_deg-thr {
    leaf deg-thr-value {
      type uint64;
      description
        "Percentage of detected errored blocks";
    }
    leaf deg-thr-type {
      type ncs_rpc_notif_deg-thr-type;
      description
        "Number of errored blocks";
    }
    leaf percentage-granularity {
      type ncs_rpc_notif_percentage-granularity;
      description
        "none";
    }
    description
      "Degraded Threshold, specify either the percentage or the number of Errored Blocks in the defined interval.
       degThrValue when type is PERCENTAGE:
       percentageGranularity is used to indicate the number of decimal points
       So if percentageGranularity is ones, a value of 1 in degThrValue would indicate 1%, a value of 10 = 10%, a value of 100 = 100%
       So if percentageGranularity is thousandths a value of 1 in degThrValue would indicate 0.001%, a value of 1000 = 1%, a value of 1000000 = 100%
       degThrValue when type is NUMBER_ERROR_BLOCKS:
       Number of Errored Blocks is captured in an integer value.";
  }

  grouping ncs_rpc_notif_uas-choice {
    leaf bidirectional {
      type boolean;
      default "true";
      description
        "none";
    }
    leaf uas {
      type uint64;
      description
        "none";
    }
    leaf nuas {
      type uint64;
      description
        "none";
    }
    leaf fuas {
      type uint64;
      description
        "none";
    }
    description
      "If bidirectional is TRUE then use the uas attribute, if bidirectional is FALSE use the nuas, and fuas attributes";
  }

  grouping ncs_rpc_notif_fec-properties {
    leaf pre-fec-ber {
      type uint64;
      description
        "counter: bit error rate before correction by FEC";
    }
    leaf post-fec-ber {
      type uint64;
      description
        "counter: bit error rate after correction by FEC";
    }
    leaf corrected-bytes {
      type uint64;
      description
        "Bytes corrected between those that were received corrupted";
    }
    leaf corrected-bits {
      type uint64;
      description
        "Bits corrected between those that were received corrupted";
    }
    leaf uncorrectable-bytes {
      type uint64;
      description
        "Bytes that could not be corrected by FEC";
    }
    leaf uncorrectable-bits {
      type uint64;
      description
        "Bits that could not be corrected by FEC";
    }
    description
      "none";
  }

  grouping live_ncs_odu-termination-and-client-adaptation-pac {
    leaf opu-tributary-slot-size {
      type live_ncs_odu-slot-size;
      description
        "This attribute is applicable for ODU2 and ODU3 CTP only. It indicates the slot size of the ODU CTP.";
    }
    leaf auto-payload-type {
      type boolean;
      description
        "This attribute is applicable when the ODU CTP object instance represents a lower order ODU CTP Source at the client layer of the ODUP/ODUj-21 adaptation function. The value of true of this attribute configures that the adaptation source function shall fall back to the payload type PT=20 if the conditions specified in 14.3.10.1/G.798 are satisfied. ";
    }
    leaf configured-client-type {
      type tapi-dsr:live_ncs_digital-signal-type;
      description
        "This attribute configures the type of the client CTP of the server ODU TTP.";
    }
    leaf configured-mapping-type {
      type live_ncs_mapping-type;
      description
        "This attributes indicates the configured mapping type.";
    }
    container accepted-payload-type {
      uses live_ncs_odu-payload-type;
      description
        "This attribute is applicable when the ODU CTP object instance represents a lower order ODU CTP Sink at the client layer of the ODUP/ODU[i]j or ODUP/ODUj-21 adaptation function.
         This attribute is a 2-digit Hex code that indicates the new accepted payload type.
         Valid values are defined in Table 15-8 of ITU-T Recommendation G.709 with one additional value UN_INTERPRETABLE.";
    }
    container fec-parameters {
      uses live_ncs_fec-properties;
      description
        "none";
    }
    leaf-list odu-cn-effective-time-slot-list {
      type uint64;
      description
        "This attribute contains a set of distinct (i.e. unique) integers (e.g. 2, 3, 5, 9, 15, 34 representing the tributary slots TS#1.2, TS#1.3, TS#1.5, TS#1.9, TS#1.15, and TS#2.14)
         which represents the list of effective time slots which are available for carrying ODUk clients.
         Each entry in the list is an integer value (P) representing the time slot name TS#A.B (see ITU-T Recommendation G.709 (v5) Clause 20.1).
         The mapping between P and A & B is: A = [P/20] + 1; B = P - (P/20]*20; where the sqaure bracket represents the whole integer.";
    }
    description
      "This Pac contains the attributes associated with the client adaptation function of the server layer TTP
       It is present only if the CEP contains a TTP";
  }

  grouping live_ncs_odu-connection-end-point-spec {
    container odu-common {
      uses live_ncs_odu-common-pac;
      description
        "none";
    }
    container odu-term-and-adapter {
      uses live_ncs_odu-termination-and-client-adaptation-pac;
      description
        "none";
    }
    container odu-ctp {
      uses live_ncs_odu-ctp-pac;
      description
        "none";
    }
    container odu-protection {
      uses live_ncs_odu-protection-pac;
      description
        "none";
    }
    description
      "none";
  }

  grouping live_ncs_odu-pool-pac {
    leaf client-capacity {
      type uint64;
      description
        "none";
    }
    leaf max-client-instances {
      type uint64;
      description
        "none";
    }
    leaf max-client-size {
      type uint64;
      description
        "none";
    }
    description
      "none";
  }

  grouping live_ncs_odu-node-edge-point-spec {
    container odu-pool {
      uses live_ncs_odu-pool-pac;
      description
        "none";
    }
    description
      "none";
  }

  grouping live_ncs_odu-ctp-pac {
    leaf-list tributary-slot-list {
      type uint64;
      description
        "ITU-T G.875 (v5)
         This attribute contains a set of distinct (i.e. unique) integers (e.g. 2, 3, 5, 9, 15 representing the tributary slots TS#2, TS#3, TS#5, TS#9 and TS#15) which represents the resources occupied by the ODUk CTP (e.g. an ODUflex with a bit rate of 6.25G setup over an HO-ODUk).
         This attribute applies when the ODUk CTP is carried by a sever layer ODU TTP object. It will not apply if this ODUk CTP object is directly carried by an OTUk TTP object (i.e. OTUk has no tributary slots).
         The upper bound of the integer allowed in this set and its relationship with the tributary slots are a function of the ODU server layer to which the ODUk CTP is carried over.
         In case the ODU server layer is an HO-ODUk, each entry in the list is an integer value (i) representing the tributary slot name TS#i and the upper bound is the maximum number of tributary slots within the HO-ODUk (see ITU-T Recommendation G.709 (v5) clause 19).
         Thus, for example, M=8/32/80 for ODU2/ODU3/ODU4 server layers (respectively) using 1.25G slot size.
         In case the ODU server layer is an ODUCn, each entry in the list is an integer value (P) representing the time slot name TS#A.B (e.g. 2, 3, 5, 9, 15, 34 representing the tributary slots TS#1.2, TS#1.3, TS#1.5, TS#1.9, TS#1.15, and TS#2.14) and the upper und is 20*n (see ITU-T Recommendation G.709 (v5) Clause 20.1).
         The mapping between P and A & B is: A = [P/20] + 1; B = P - (P/20]*20; where the square bracket represents the whole integer. Note that the value of this attribute can be changed only in the case of ODUflex and has to be through specific operations (i.e. not be changing the attribute tributarySlotList directly).";
    }
    leaf tributary-port-number {
      type uint64;
      description
        "This attribute identifies the tributary port number that is associated with the ODUk CTP. This attribute applies when the ODUk CTP is multiplexed into a server layer ODU TTP object.
         It will not apply if this ODUk CTP object is directly mapped into an OTUk TTP object (i.e. OTUk has no tributary slots).
         The upper bound of the integer allowed in this set is a function of the ODU server layer into which the ODUk CTP is multiplexed.
         In case the ODU server layer is an HO-ODUk, the upper bound is the maximum number of tributary slots within the HO-ODUk (see ITU-T Recommendation G.709 (v5) clause 19.4.1).
         Thus, for example, M=8/32/80 for ODU2/ODU3/ODU4 server layers (respectively) using 1.25G slot size.
         In case the ODU server layer is an ODUCn, the upper bound is M=10*n (see ITU-T Recommendation G.709 (v5) Clause 20.4.1).
         range of type : The value range depends on the size of the Tributary Port Number (TPN) field used which depends on th server-layer ODU or OTU.
         In case of ODUk mapping into OTUk, there is no TPN field, so the tributaryPortNumber shall be zero.
         In case of LO ODUj mapping over ODU1, ODU2 or ODU3, the TPN is encoded in a 6-bit field so the value range is 0-63. See clause 14.4.1/G.709-2016.
         In case of LO ODUj mapping over ODU4, the TPN is encoded in a 7-bit field so the value range is 0-127. See clause 14.4.1.4/G.709-2016.
         In case of ODUk mapping over ODUCn, the TPN is encoded in a 14-bit field so the value range is 0-16383. See clause 20.4.1.1/G.709-2016.
        ";
    }
    leaf accepted-msi {
      type string;
      description
        "This attribute is applicable when the ODU CTP object instance represents a lower order ODU1 or ODU2 CTP Sink at the client layer of the ODU3P/ODU12 adaptation function or represents a lower order ODUj CTP Sink at the client layer of the ODUP/ODUj-21 adaptation function. This attribute is a 1-byte field that represents the accepted multiplex structure of the adaptation function. ";
    }
    description
      "This Pac contains the attributes associated with the CTP
       It is present only if the CEP contains a CTP";
  }

  grouping live_ncs_odu-mep-spec {
    container odu-mep {
      uses live_ncs_odu-mep-pac;
      description
        "none";
    }
    container odu-ncm {
      uses live_ncs_odu-ncm-pac;
      description
        "none";
    }
    container odu-tcm {
      uses live_ncs_odu-tcm-mep-pac;
      description
        "none";
    }
    container odu-defect {
      uses live_ncs_odu-defect-pac;
      description
        "none";
    }
    container odu-pm {
      uses live_ncs_odu-pm-pac;
      description
        "none";
    }
    description
      "none";
  }

  grouping live_ncs_odu-protection-pac {
    leaf aps-enable {
      type boolean;
      // NCS drop default statement
      description
        "This attribute is for enabling/disabling the automatic protection switching (APS) capability at the transport adaptation function that is represented by the ODU_ConnectionTerminationPoint object class. It triggers the MI_APS_EN signal to the transport adaptation function.";
    }
    leaf aps-level {
      type uint64;
      description
        "This attribute is for configuring the automatic protection switching (APS) level that should operate at the transport adaptation function that is represented by the ODU_ConnectionTerminationPoint object class. It triggers the MI_APS_LVL signal to the transport adaptation function. The value 0 means path and the values 1 through 6 mean TCM level 1 through 6 respectively.";
    }
    description
      "none";
  }

  grouping live_ncs_odu-ncm-pac {
    leaf-list tcm-fields-in-use {
      type uint64;
      description
        "This attribute indicates the used TCM fields of the ODU OH.";
    }
    description
      "none";
  }

  grouping live_ncs_odu-tcm-mep-pac {
    leaf tcm-extension {
      type live_ncs_tcm-extension;
      description
        "none";
    }
    leaf tcm-mode {
      type live_ncs_tcm-mode;
      description
        "This attribute specifies the TCM mode at the entity. Valid values are: Operational, Monitor, and Transparent.";
    }
    leaf codirectional {
      type boolean;
      description
        "This attribute specifies the directionality of the ODUT MEP with respect to the associated ODU CEP. The value of TRUE means that the sink part of the ODUT MEP terminates the same signal direction as the sink part of the ODU CEP. The Source part behaves similarly. This attribute is meaningful only on objects instantiated under ODU CEP, and at least one among ODU CEP and the subordinate object is bidirectional.";
    }
    leaf ac-status-source {
      type live_ncs_tcm-status;
      description
        "This attribute indicates the status of the accepted TCM. ";
    }
    leaf ac-status-sink {
      type live_ncs_tcm-status;
      description
        "This attribute indicates the status of the accepted TCM. ";
    }
    leaf admin-state-source {
      type tapi-common:live_ncs_administrative-state;
      description
        "This attribute provides the capability to provision the LOCK signal at the source, which is one of the ODU maintenance signals.  When a Tandem Connection endpoint is set to admin state locked, it will insert the ODU-LCK signal in the source direction.";
    }
    leaf admin-state-sink {
      type tapi-common:live_ncs_administrative-state;
      description
        "This attribute provides the capability to provision the LOCK signal at the sink, which is one of the ODU maintenance signals. When a Tandem Connection endpoint is set to admin state locked, it will insert the ODU-LCK signal in the downstream direction.";
    }
    uses live_ncs_odu-tcm-mip-pac;
    description
      "none";
  }

  grouping live_ncs_odu-mip-spec {
    container odu-mip {
      uses live_ncs_odu-mip-pac;
      description
        "none";
    }
    container odu-ncm {
      uses live_ncs_odu-ncm-pac;
      description
        "none";
    }
    container odu-tcm {
      uses live_ncs_odu-tcm-mip-pac;
      description
        "none";
    }
    container odu-pm {
      uses live_ncs_odu-pm-pac;
      description
        "none";
    }
    container odu-defect {
      uses live_ncs_odu-defect-pac;
      description
        "none";
    }
    description
      "none";
  }

  grouping live_ncs_odu-mip-pac {
    leaf acti {
      type string;
      description
        "The Trail Trace Identifier (TTI) information recovered (Accepted) from the TTI overhead position at the sink of a trail.";
    }
    leaf ex-dapi {
      type string;
      description
        "The Expected Destination Access Point Identifier (ExDAPI), provisioned by the managing system, to be compared with the TTI accepted at the overhead position of the sink for the purpose of checking the integrity of connectivity.";
    }
    leaf ex-sapi {
      type string;
      description
        "The Expected Source Access Point Identifier (ExSAPI), provisioned by the managing system, to be compared with the TTI accepted at the overhead position of the sink for the purpose of checking the integrity of connectivity.
        ";
    }
    leaf tim-act-disabled {
      type boolean;
      // NCS drop default statement
      description
        "This attribute provides the control capability for the managing system to enable or disable the Consequent Action function when detecting Trace Identifier Mismatch (TIM) at the trail termination sink.";
    }
    leaf tim-det-mode {
      type live_ncs_tim-det-mo;
      description
        "This attribute indicates the mode of the Trace Identifier Mismatch (TIM) Detection function allowed values: OFF, SAPIonly, DAPIonly, SAPIandDAPI";
    }
    leaf deg-m {
      type uint64;
      description
        "This attribute indicates the threshold level for declaring a Degraded Signal defect (dDEG). A dDEG shall be declared if DegM consecutive bad PM Seconds are detected.";
    }
    container deg-thr {
      uses live_ncs_deg-thr;
      description
        "This attribute indicates the threshold level for declaring a performance monitoring (PM) Second to be bad. The value of the threshold can be provisioned in terms of number of errored blocks or in terms of percentage of errored blocks. For percentage-based specification, in order to support provision of less than 1%, the specification consists of two fields. The first field indicates the granularity of percentage. For examples, in 1%, in 0.1%, or in 0.01%, etc. The second field indicates the multiple of the granularity. For number of errored block based, the value is a positive integer.";
    }
    description
      "none";
  }

  grouping live_ncs_odu-tcm-mip-pac {
    leaf tcm-field {
      type uint64;
      description
        "This attribute indicates the tandem connection monitoring field of the ODU OH.";
    }
    description
      "none";
  }

  grouping live_ncs_odu-mep-pac {
    leaf dm-source {
      type boolean;
      description
        "This attribute is for configuring the delay measurement process at the trail termination function represented by the subject TTP object class. It models the MI_DM_Source MI signal. If MI_DM_Source is false, then the value of the DMp bit is determined by the RI_DM. If MI_DM_Source is true, then the value of the DMp bit is set to MI_DMValue.";
    }
    leaf dm-value {
      type boolean;
      description
        "This attribute is for setting the DMp and DMti bits of the delay measurement process. The value of 'true' sets the DMp and DMti bits to 0 and the value of 'false' to 1.";
    }
    leaf txti {
      type string;
      description
        "The Trail Trace Identifier (TTI) information, provisioned by the managing system at the termination source, to be placed in the TTI overhead position of the source of a trail for transmission.
        ";
    }
    uses live_ncs_odu-mip-pac;
    description
      "none";
  }

  grouping live_ncs_odu-common-pac {
    leaf odu-type {
      type live_ncs_odu-type;
      description
        "This attribute specifies the type of the ODU termination point.";
    }
    leaf odu-rate {
      type uint64;
      description
        "This attribute indicates the rate of the ODU termination point in Kbits/s.
         This attribute is Set at create; i.e., once created it cannot be changed directly.
         In case of resizable ODU flex, its value can be changed via HAO (not directly on the attribute).
         This attribute indicates the rate of the ODU termination point.
         Valid values shall be consistent with the oduType configuration as shown in Table 7-2/G.709 v5.
         Setting this value for fixed-rate ODUk types (e.g., ODU0), is optional.
         The default value is derived from the configured oduType, as defined in Table 7-2/G.709 v5.
         Setting this value for ODUCn type is optional. The default value is derived from the configured n of the ODUCn as defined in Table 7-2/G.709 v5.";
    }
    leaf odu-rate-tolerance {
      type uint64;
      description
        "This attribute indicates the rate tolerance of the ODU termination point.
         Valid values are real value in the unit of ppm.
         Standardized values are defined in Table 7-2/G.709.";
    }
    leaf number-of-odu-c {
      type uint64;
      // NCS drop default statement
      description
        "This attribute specifies the number of ODUC instances of the ODUCn.";
    }
    description
      "none";
  }

  grouping live_ncs_odu-pm-pac {
    leaf n-bbe {
      type uint64;
      description
        "Near-end Background Block Error";
    }
    leaf f-bbe {
      type uint64;
      description
        "Far-end Background Block Error";
    }
    leaf n-ses {
      type uint64;
      description
        "Near-end Severely Errored Second";
    }
    leaf f-ses {
      type uint64;
      description
        "Far-end Severely Errored Second";
    }
    container uas {
      uses live_ncs_uas-choice;
      description
        "UnAvailable Second";
    }
    description
      "Instance of this object class contains the ODUP layer-specific Current Data. This object class is a subclass of the OTN_CurrentData object class.
       PM data attributes: fBbe, fSes, nBbe, nSes. uas";
  }

  grouping live_ncs_odu-defect-pac {
    leaf bdi {
      type boolean;
      description
        "Backward Defect Indication";
    }
    leaf deg {
      type boolean;
      description
        "Signal Degraded";
    }
    leaf lck {
      type boolean;
      description
        "Locked";
    }
    leaf oci {
      type boolean;
      description
        "Open Connection Indicator";
    }
    leaf ssf {
      type boolean;
      description
        "Server Signal Failure";
    }
    leaf tim {
      type boolean;
      description
        "Trail Trace Identifier Mismatch";
    }
    description
      "The valid list of defects raised on the entity. If the value of any attribute is true, then the corresponding defect is raised.";
  }

  grouping live_ncs_odu-connectivity-service-end-point-spec {
    container odu-csep-ctp-pac {
      uses live_ncs_odu-csep-ctp-pac;
      description
        "none";
    }
    container odu-csep-ttp-pac {
      uses live_ncs_odu-csep-ttp-pac;
      description
        "none";
    }
    container odu-csep-common-pac {
      uses live_ncs_odu-csep-common-pac;
      description
        "none";
    }
    description
      "none";
  }

  grouping live_ncs_odu-csep-ctp-pac {
    leaf tributary-port-number {
      type uint64;
      description
        "This attribute identifies the tributary port number that is associated with the ODUk CTP. This attribute applies when the ODUk CTP is multiplexed into a server layer ODU TTP object.
         It will not apply if this ODUk CTP object is directly mapped into an OTUk TTP object (i.e. OTUk has no tributary slots).
         The upper bound of the integer allowed in this set is a function of the ODU server layer into which the ODUk CTP is multiplexed.
         In case the ODU server layer is an HO-ODUk, the upper bound is the maximum number of tributary slots within the HO-ODUk (see ITU-T Recommendation G.709 (v5) clause 19.4.1).
         Thus, for example, M=8/32/80 for ODU2/ODU3/ODU4 server layers (respectively) using 1.25G slot size.
         In case the ODU server layer is an ODUCn, the upper bound is M=10*n (see ITU-T Recommendation G.709 (v5) Clause 20.4.1).
         range of type : The value range depends on the size of the Tributary Port Number (TPN) field used which depends on th server-layer ODU or OTU.
         In case of ODUk mapping into OTUk, there is no TPN field, so the tributaryPortNumber shall be zero.
         In case of LO ODUj mapping over ODU1, ODU2 or ODU3, the TPN is encoded in a 6-bit field so the value range is 0-63. See clause 14.4.1/G.709-2016.
         In case of LO ODUj mapping over ODU4, the TPN is encoded in a 7-bit field so the value range is 0-127. See clause 14.4.1.4/G.709-2016.
         In case of ODUk mapping over ODUCn, the TPN is encoded in a 14-bit field so the value range is 0-16383. See clause 20.4.1.1/G.709-2016.
        ";
    }
    leaf-list tributary-slot-list {
      type uint64;
      description
        "ITU-T G.875 (v5)
         This attribute contains a set of distinct (i.e. unique) integers (e.g. 2, 3, 5, 9, 15 representing the tributary slots TS#2, TS#3, TS#5, TS#9 and TS#15) which represents the resources occupied by the ODUk CTP (e.g. an ODUflex with a bit rate of 6.25G setup over an HO-ODUk).
         This attribute applies when the ODUk CTP is carried by a sever layer ODU TTP object. It will not apply if this ODUk CTP object is directly carried by an OTUk TTP object (i.e. OTUk has no tributary slots).
         The upper bound of the integer allowed in this set and its relationship with the tributary slots are a function of the ODU server layer to which the ODUk CTP is carried over.
         In case the ODU server layer is an HO-ODUk, each entry in the list is an integer value (i) representing the tributary slot name TS#i and the upper bound is the maximum number of tributary slots within the HO-ODUk (see ITU-T Recommendation G.709 (v5) clause 19).
         Thus, for example, M=8/32/80 for ODU2/ODU3/ODU4 server layers (respectively) using 1.25G slot size.
         In case the ODU server layer is an ODUCn, each entry in the list is an integer value (P) representing the time slot name TS#A.B (e.g. 2, 3, 5, 9, 15, 34 representing the tributary slots TS#1.2, TS#1.3, TS#1.5, TS#1.9, TS#1.15, and TS#2.14) and the upper und is 20*n (see ITU-T Recommendation G.709 (v5) Clause 20.1).
         The mapping between P and A & B is: A = [P/20] + 1; B = P - (P/20]*20; where the square bracket represents the whole integer. Note that the value of this attribute can be changed only in the case of ODUflex and has to be through specific operations (i.e. not be changing the attribute tributarySlotList directly).";
    }
    description
      "none";
  }

  grouping live_ncs_odu-csep-ttp-pac {
    leaf configured-mapping-type {
      type live_ncs_mapping-type;
      description
        "This attributes indicates the configured mapping type.";
    }
    leaf configured-client-type {
      type tapi-dsr:live_ncs_digital-signal-type;
      description
        "This attribute configures the type of the client CTP of the server ODU TTP.";
    }
    description
      "none";
  }

  grouping live_ncs_odu-csep-common-pac {
    leaf odu-type {
      type live_ncs_odu-type;
      description
        "This attribute specifies the type of the ODU termination point.";
    }
    leaf odu-rate {
      type uint64;
      description
        "This attribute indicates the rate of the ODU termination point in Kbits/s.
         This attribute is Set at create; i.e., once created it cannot be changed directly.
         In case of resizable ODU flex, its value can be changed via HAO (not directly on the attribute).
         This attribute indicates the rate of the ODU termination point.
         Valid values shall be consistent with the oduType configuration as shown in Table 7-2/G.709 v5.
         Setting this value for fixed-rate ODUk types (e.g., ODU0), is optional.
         The default value is derived from the configured oduType, as defined in Table 7-2/G.709 v5.
         Setting this value for ODUCn type is optional. The default value is derived from the configured n of the ODUCn as defined in Table 7-2/G.709 v5.";
    }
    leaf opu-tributary-slot-size {
      type live_ncs_odu-slot-size;
      description
        "This attribute is applicable for ODU2 and ODU3 CTP only. It indicates the slot size of the ODU CTP.";
    }
    leaf number-of-odu-c {
      type uint64;
      // NCS drop default statement
      description
        "This attribute specifies the number of ODUC instances of the ODUCn.";
    }
    description
      "none";
  }

  grouping live_ncs_odu-payload-type {
    leaf named-payload-type {
      type live_ncs_odu-named-payload-type;
      description
        "none";
    }
    leaf hex-payload-type {
      type uint64;
      description
        "none";
    }
    description
      "none";
  }

  grouping live_ncs_deg-thr {
    leaf deg-thr-value {
      type uint64;
      description
        "Percentage of detected errored blocks";
    }
    leaf deg-thr-type {
      type live_ncs_deg-thr-type;
      description
        "Number of errored blocks";
    }
    leaf percentage-granularity {
      type live_ncs_percentage-granularity;
      description
        "none";
    }
    description
      "Degraded Threshold, specify either the percentage or the number of Errored Blocks in the defined interval.
       degThrValue when type is PERCENTAGE:
       percentageGranularity is used to indicate the number of decimal points
       So if percentageGranularity is ones, a value of 1 in degThrValue would indicate 1%, a value of 10 = 10%, a value of 100 = 100%
       So if percentageGranularity is thousandths a value of 1 in degThrValue would indicate 0.001%, a value of 1000 = 1%, a value of 1000000 = 100%
       degThrValue when type is NUMBER_ERROR_BLOCKS:
       Number of Errored Blocks is captured in an integer value.";
  }

  grouping live_ncs_uas-choice {
    leaf bidirectional {
      type boolean;
      // NCS drop default statement
      description
        "none";
    }
    leaf uas {
      type uint64;
      description
        "none";
    }
    leaf nuas {
      type uint64;
      description
        "none";
    }
    leaf fuas {
      type uint64;
      description
        "none";
    }
    description
      "If bidirectional is TRUE then use the uas attribute, if bidirectional is FALSE use the nuas, and fuas attributes";
  }

  grouping live_ncs_fec-properties {
    leaf pre-fec-ber {
      type uint64;
      description
        "counter: bit error rate before correction by FEC";
    }
    leaf post-fec-ber {
      type uint64;
      description
        "counter: bit error rate after correction by FEC";
    }
    leaf corrected-bytes {
      type uint64;
      description
        "Bytes corrected between those that were received corrupted";
    }
    leaf corrected-bits {
      type uint64;
      description
        "Bits corrected between those that were received corrupted";
    }
    leaf uncorrectable-bytes {
      type uint64;
      description
        "Bytes that could not be corrected by FEC";
    }
    leaf uncorrectable-bits {
      type uint64;
      description
        "Bits that could not be corrected by FEC";
    }
    description
      "none";
  }

  grouping odu-termination-and-client-adaptation-pac {
    // NCS drop config false leaf 'opu-tributary-slot-size'
    // NCS drop config false leaf 'auto-payload-type'
    // NCS drop config false leaf 'configured-client-type'
    // NCS drop config false leaf 'configured-mapping-type'
    // NCS drop config false container 'accepted-payload-type'
    // NCS drop config false container 'fec-parameters'
    leaf-list odu-cn-effective-time-slot-list {
      type uint64;
      description
        "This attribute contains a set of distinct (i.e. unique) integers (e.g. 2, 3, 5, 9, 15, 34 representing the tributary slots TS#1.2, TS#1.3, TS#1.5, TS#1.9, TS#1.15, and TS#2.14)
         which represents the list of effective time slots which are available for carrying ODUk clients.
         Each entry in the list is an integer value (P) representing the time slot name TS#A.B (see ITU-T Recommendation G.709 (v5) Clause 20.1).
         The mapping between P and A & B is: A = [P/20] + 1; B = P - (P/20]*20; where the sqaure bracket represents the whole integer.";
    }
    description
      "This Pac contains the attributes associated with the client adaptation function of the server layer TTP
       It is present only if the CEP contains a TTP";
  }

  grouping odu-connection-end-point-spec {
    container odu-common {
      uses odu-common-pac;
      description
        "none";
    }
    // NCS drop config false container 'odu-term-and-adapter'
    // NCS drop config false container 'odu-ctp'
    // NCS drop config false container 'odu-protection'
    description
      "none";
  }

  grouping odu-pool-pac {
    leaf client-capacity {
      type uint64;
      description
        "none";
    }
    // NCS drop config false leaf 'max-client-instances'
    // NCS drop config false leaf 'max-client-size'
    description
      "none";
  }

  grouping odu-node-edge-point-spec {
    // NCS drop config false container 'odu-pool'
    description
      "none";
  }

  grouping odu-ctp-pac {
    // NCS drop config false leaf-list 'tributary-slot-list'
    // NCS drop config false leaf 'tributary-port-number'
    // NCS drop config false leaf 'accepted-msi'
    description
      "This Pac contains the attributes associated with the CTP
       It is present only if the CEP contains a CTP";
  }

  grouping odu-mep-spec {
    container odu-mep {
      uses odu-mep-pac;
      description
        "none";
    }
    // NCS drop config false container 'odu-ncm'
    // NCS drop config false container 'odu-tcm'
    container odu-defect {
      uses odu-defect-pac;
      description
        "none";
    }
    container odu-pm {
      uses odu-pm-pac;
      description
        "none";
    }
    description
      "none";
  }

  grouping odu-protection-pac {
    leaf aps-enable {
      type boolean;
      default "true";
      description
        "This attribute is for enabling/disabling the automatic protection switching (APS) capability at the transport adaptation function that is represented by the ODU_ConnectionTerminationPoint object class. It triggers the MI_APS_EN signal to the transport adaptation function.";
    }
    leaf aps-level {
      type uint64;
      description
        "This attribute is for configuring the automatic protection switching (APS) level that should operate at the transport adaptation function that is represented by the ODU_ConnectionTerminationPoint object class. It triggers the MI_APS_LVL signal to the transport adaptation function. The value 0 means path and the values 1 through 6 mean TCM level 1 through 6 respectively.";
    }
    description
      "none";
  }

  grouping odu-ncm-pac {
    // NCS drop config false leaf-list 'tcm-fields-in-use'
    description
      "none";
  }

  grouping odu-tcm-mep-pac {
    leaf tcm-extension {
      type tcm-extension;
      description
        "none";
    }
    leaf tcm-mode {
      type tcm-mode;
      description
        "This attribute specifies the TCM mode at the entity. Valid values are: Operational, Monitor, and Transparent.";
    }
    // NCS drop config false leaf codirectional
    // NCS drop config false leaf 'ac-status-source'
    // NCS drop config false leaf 'ac-status-sink'
    leaf admin-state-source {
      type tapi-common:administrative-state;
      description
        "This attribute provides the capability to provision the LOCK signal at the source, which is one of the ODU maintenance signals.  When a Tandem Connection endpoint is set to admin state locked, it will insert the ODU-LCK signal in the source direction.";
    }
    leaf admin-state-sink {
      type tapi-common:administrative-state;
      description
        "This attribute provides the capability to provision the LOCK signal at the sink, which is one of the ODU maintenance signals. When a Tandem Connection endpoint is set to admin state locked, it will insert the ODU-LCK signal in the downstream direction.";
    }
    uses odu-tcm-mip-pac;
    description
      "none";
  }

  grouping odu-mip-spec {
    // NCS drop config false container 'odu-mip'
    // NCS drop config false container 'odu-ncm'
    // NCS drop config false container 'odu-tcm'
    container odu-pm {
      uses odu-pm-pac;
      description
        "none";
    }
    container odu-defect {
      uses odu-defect-pac;
      description
        "none";
    }
    description
      "none";
  }

  grouping odu-mip-pac {
    // NCS drop config false leaf acti
    leaf ex-dapi {
      type string;
      description
        "The Expected Destination Access Point Identifier (ExDAPI), provisioned by the managing system, to be compared with the TTI accepted at the overhead position of the sink for the purpose of checking the integrity of connectivity.";
    }
    leaf ex-sapi {
      type string;
      description
        "The Expected Source Access Point Identifier (ExSAPI), provisioned by the managing system, to be compared with the TTI accepted at the overhead position of the sink for the purpose of checking the integrity of connectivity.
        ";
    }
    leaf tim-act-disabled {
      type boolean;
      default "true";
      description
        "This attribute provides the control capability for the managing system to enable or disable the Consequent Action function when detecting Trace Identifier Mismatch (TIM) at the trail termination sink.";
    }
    leaf tim-det-mode {
      type tim-det-mo;
      description
        "This attribute indicates the mode of the Trace Identifier Mismatch (TIM) Detection function allowed values: OFF, SAPIonly, DAPIonly, SAPIandDAPI";
    }
    leaf deg-m {
      type uint64;
      description
        "This attribute indicates the threshold level for declaring a Degraded Signal defect (dDEG). A dDEG shall be declared if DegM consecutive bad PM Seconds are detected.";
    }
    container deg-thr {
      uses deg-thr;
      description
        "This attribute indicates the threshold level for declaring a performance monitoring (PM) Second to be bad. The value of the threshold can be provisioned in terms of number of errored blocks or in terms of percentage of errored blocks. For percentage-based specification, in order to support provision of less than 1%, the specification consists of two fields. The first field indicates the granularity of percentage. For examples, in 1%, in 0.1%, or in 0.01%, etc. The second field indicates the multiple of the granularity. For number of errored block based, the value is a positive integer.";
    }
    description
      "none";
  }

  grouping odu-tcm-mip-pac {
    // NCS drop config false leaf 'tcm-field'
    description
      "none";
  }

  grouping odu-mep-pac {
    leaf dm-source {
      type boolean;
      description
        "This attribute is for configuring the delay measurement process at the trail termination function represented by the subject TTP object class. It models the MI_DM_Source MI signal. If MI_DM_Source is false, then the value of the DMp bit is determined by the RI_DM. If MI_DM_Source is true, then the value of the DMp bit is set to MI_DMValue.";
    }
    leaf dm-value {
      type boolean;
      description
        "This attribute is for setting the DMp and DMti bits of the delay measurement process. The value of 'true' sets the DMp and DMti bits to 0 and the value of 'false' to 1.";
    }
    leaf txti {
      type string;
      description
        "The Trail Trace Identifier (TTI) information, provisioned by the managing system at the termination source, to be placed in the TTI overhead position of the source of a trail for transmission.
        ";
    }
    uses odu-mip-pac;
    description
      "none";
  }

  grouping odu-common-pac {
    // NCS drop config false leaf 'odu-type'
    // NCS drop config false leaf 'odu-rate'
    // NCS drop config false leaf 'odu-rate-tolerance'
    leaf number-of-odu-c {
      type uint64;
      default "1";
      description
        "This attribute specifies the number of ODUC instances of the ODUCn.";
    }
    description
      "none";
  }

  grouping odu-pm-pac {
    leaf n-bbe {
      type uint64;
      description
        "Near-end Background Block Error";
    }
    // NCS drop config false leaf 'f-bbe'
    leaf n-ses {
      type uint64;
      description
        "Near-end Severely Errored Second";
    }
    leaf f-ses {
      type uint64;
      description
        "Far-end Severely Errored Second";
    }
    container uas {
      uses uas-choice;
      description
        "UnAvailable Second";
    }
    description
      "Instance of this object class contains the ODUP layer-specific Current Data. This object class is a subclass of the OTN_CurrentData object class.
       PM data attributes: fBbe, fSes, nBbe, nSes. uas";
  }

  grouping odu-defect-pac {
    // NCS drop config false leaf bdi
    // NCS drop config false leaf deg
    // NCS drop config false leaf lck
    // NCS drop config false leaf oci
    // NCS drop config false leaf ssf
    // NCS drop config false leaf tim
    description
      "The valid list of defects raised on the entity. If the value of any attribute is true, then the corresponding defect is raised.";
  }

  grouping odu-connectivity-service-end-point-spec {
    container odu-csep-ctp-pac {
      uses odu-csep-ctp-pac;
      description
        "none";
    }
    container odu-csep-ttp-pac {
      uses odu-csep-ttp-pac;
      description
        "none";
    }
    container odu-csep-common-pac {
      uses odu-csep-common-pac;
      description
        "none";
    }
    description
      "none";
  }

  grouping odu-csep-ctp-pac {
    leaf tributary-port-number {
      type uint64;
      description
        "This attribute identifies the tributary port number that is associated with the ODUk CTP. This attribute applies when the ODUk CTP is multiplexed into a server layer ODU TTP object.
         It will not apply if this ODUk CTP object is directly mapped into an OTUk TTP object (i.e. OTUk has no tributary slots).
         The upper bound of the integer allowed in this set is a function of the ODU server layer into which the ODUk CTP is multiplexed.
         In case the ODU server layer is an HO-ODUk, the upper bound is the maximum number of tributary slots within the HO-ODUk (see ITU-T Recommendation G.709 (v5) clause 19.4.1).
         Thus, for example, M=8/32/80 for ODU2/ODU3/ODU4 server layers (respectively) using 1.25G slot size.
         In case the ODU server layer is an ODUCn, the upper bound is M=10*n (see ITU-T Recommendation G.709 (v5) Clause 20.4.1).
         range of type : The value range depends on the size of the Tributary Port Number (TPN) field used which depends on th server-layer ODU or OTU.
         In case of ODUk mapping into OTUk, there is no TPN field, so the tributaryPortNumber shall be zero.
         In case of LO ODUj mapping over ODU1, ODU2 or ODU3, the TPN is encoded in a 6-bit field so the value range is 0-63. See clause 14.4.1/G.709-2016.
         In case of LO ODUj mapping over ODU4, the TPN is encoded in a 7-bit field so the value range is 0-127. See clause 14.4.1.4/G.709-2016.
         In case of ODUk mapping over ODUCn, the TPN is encoded in a 14-bit field so the value range is 0-16383. See clause 20.4.1.1/G.709-2016.
        ";
    }
    leaf-list tributary-slot-list {
      type uint64;
      description
        "ITU-T G.875 (v5)
         This attribute contains a set of distinct (i.e. unique) integers (e.g. 2, 3, 5, 9, 15 representing the tributary slots TS#2, TS#3, TS#5, TS#9 and TS#15) which represents the resources occupied by the ODUk CTP (e.g. an ODUflex with a bit rate of 6.25G setup over an HO-ODUk).
         This attribute applies when the ODUk CTP is carried by a sever layer ODU TTP object. It will not apply if this ODUk CTP object is directly carried by an OTUk TTP object (i.e. OTUk has no tributary slots).
         The upper bound of the integer allowed in this set and its relationship with the tributary slots are a function of the ODU server layer to which the ODUk CTP is carried over.
         In case the ODU server layer is an HO-ODUk, each entry in the list is an integer value (i) representing the tributary slot name TS#i and the upper bound is the maximum number of tributary slots within the HO-ODUk (see ITU-T Recommendation G.709 (v5) clause 19).
         Thus, for example, M=8/32/80 for ODU2/ODU3/ODU4 server layers (respectively) using 1.25G slot size.
         In case the ODU server layer is an ODUCn, each entry in the list is an integer value (P) representing the time slot name TS#A.B (e.g. 2, 3, 5, 9, 15, 34 representing the tributary slots TS#1.2, TS#1.3, TS#1.5, TS#1.9, TS#1.15, and TS#2.14) and the upper und is 20*n (see ITU-T Recommendation G.709 (v5) Clause 20.1).
         The mapping between P and A & B is: A = [P/20] + 1; B = P - (P/20]*20; where the square bracket represents the whole integer. Note that the value of this attribute can be changed only in the case of ODUflex and has to be through specific operations (i.e. not be changing the attribute tributarySlotList directly).";
    }
    description
      "none";
  }

  grouping odu-csep-ttp-pac {
    leaf configured-mapping-type {
      type mapping-type;
      description
        "This attributes indicates the configured mapping type.";
    }
    // NCS drop config false leaf 'configured-client-type'
    description
      "none";
  }

  grouping odu-csep-common-pac {
    leaf odu-type {
      type odu-type;
      description
        "This attribute specifies the type of the ODU termination point.";
    }
    leaf odu-rate {
      type uint64;
      description
        "This attribute indicates the rate of the ODU termination point in Kbits/s.
         This attribute is Set at create; i.e., once created it cannot be changed directly.
         In case of resizable ODU flex, its value can be changed via HAO (not directly on the attribute).
         This attribute indicates the rate of the ODU termination point.
         Valid values shall be consistent with the oduType configuration as shown in Table 7-2/G.709 v5.
         Setting this value for fixed-rate ODUk types (e.g., ODU0), is optional.
         The default value is derived from the configured oduType, as defined in Table 7-2/G.709 v5.
         Setting this value for ODUCn type is optional. The default value is derived from the configured n of the ODUCn as defined in Table 7-2/G.709 v5.";
    }
    leaf opu-tributary-slot-size {
      type odu-slot-size;
      description
        "This attribute is applicable for ODU2 and ODU3 CTP only. It indicates the slot size of the ODU CTP.";
    }
    leaf number-of-odu-c {
      type uint64;
      default "1";
      description
        "This attribute specifies the number of ODUC instances of the ODUCn.";
    }
    description
      "none";
  }

  grouping odu-payload-type {
    leaf named-payload-type {
      type odu-named-payload-type;
      description
        "none";
    }
    leaf hex-payload-type {
      type uint64;
      description
        "none";
    }
    description
      "none";
  }

  grouping deg-thr {
    leaf deg-thr-value {
      type uint64;
      description
        "Percentage of detected errored blocks";
    }
    leaf deg-thr-type {
      type deg-thr-type;
      description
        "Number of errored blocks";
    }
    leaf percentage-granularity {
      type percentage-granularity;
      description
        "none";
    }
    description
      "Degraded Threshold, specify either the percentage or the number of Errored Blocks in the defined interval.
       degThrValue when type is PERCENTAGE:
       percentageGranularity is used to indicate the number of decimal points
       So if percentageGranularity is ones, a value of 1 in degThrValue would indicate 1%, a value of 10 = 10%, a value of 100 = 100%
       So if percentageGranularity is thousandths a value of 1 in degThrValue would indicate 0.001%, a value of 1000 = 1%, a value of 1000000 = 100%
       degThrValue when type is NUMBER_ERROR_BLOCKS:
       Number of Errored Blocks is captured in an integer value.";
  }

  grouping uas-choice {
    leaf bidirectional {
      type boolean;
      default "true";
      description
        "none";
    }
    leaf uas {
      type uint64;
      description
        "none";
    }
    leaf nuas {
      type uint64;
      description
        "none";
    }
    leaf fuas {
      type uint64;
      description
        "none";
    }
    description
      "If bidirectional is TRUE then use the uas attribute, if bidirectional is FALSE use the nuas, and fuas attributes";
  }

  grouping fec-properties {
    leaf pre-fec-ber {
      type uint64;
      description
        "counter: bit error rate before correction by FEC";
    }
    leaf post-fec-ber {
      type uint64;
      description
        "counter: bit error rate after correction by FEC";
    }
    leaf corrected-bytes {
      type uint64;
      description
        "Bytes corrected between those that were received corrupted";
    }
    leaf corrected-bits {
      type uint64;
      description
        "Bits corrected between those that were received corrupted";
    }
    leaf uncorrectable-bytes {
      type uint64;
      description
        "Bytes that could not be corrected by FEC";
    }
    leaf uncorrectable-bits {
      type uint64;
      description
        "Bits that could not be corrected by FEC";
    }
    description
      "none";
  }

  augment "/ncs:devices/ncs:device/ncs:live-status/tapi-common:context/tapi-topology:topology-context/tapi-topology:topology/tapi-topology:node/tapi-topology:owned-node-edge-point" {
    container odu-node-edge-point-spec {
      tailf:ncs-device-type "netconf";
      tailf:display-when "not(../../../../../../../ncs:module) or ../../../../../../../ncs:module[ncs:name='tapi-odu'] or (../../../../../../../ncs:live-status-protocol[not(ncs:capability)]) or (../../../../../../../ncs:live-status-protocol/ncs:capability/ncs:module[.='tapi-odu'])";
      uses live_ncs_odu-node-edge-point-spec;
      description
        "Augments the base LayerProtocol information in NodeEdgePoint with ODU-specific information";
    }
    description
      "Augments the base LayerProtocol information in NodeEdgePoint with ODU-specific information";
  }
  augment "/ncs:devices/ncs:device/ncs:live-status/tapi-common:context/tapi-topology:topology-context/tapi-topology:topology/tapi-topology:node/tapi-topology:owned-node-edge-point/tapi-connectivity:cep-list/tapi-connectivity:connection-end-point" {
    container odu-connection-end-point-spec {
      tailf:ncs-device-type "netconf";
      tailf:display-when "not(../../../../../../../../../ncs:module) or ../../../../../../../../../ncs:module[ncs:name='tapi-odu'] or (../../../../../../../../../ncs:live-status-protocol[not(ncs:capability)]) or (../../../../../../../../../ncs:live-status-protocol/ncs:capability/ncs:module[.='tapi-odu'])";
      uses live_ncs_odu-connection-end-point-spec;
      description
        "none";
    }
    description
      "none";
  }
  augment "/ncs:devices/ncs:device/ncs:live-status/tapi-common:context/tapi-oam:oam-context/tapi-oam:meg/tapi-oam:mep" {
    container odu-connection-end-point-spec {
      tailf:ncs-device-type "netconf";
      tailf:display-when "not(../../../../../../ncs:module) or ../../../../../../ncs:module[ncs:name='tapi-odu'] or (../../../../../../ncs:live-status-protocol[not(ncs:capability)]) or (../../../../../../ncs:live-status-protocol/ncs:capability/ncs:module[.='tapi-odu'])";
      uses live_ncs_odu-connection-end-point-spec;
      description
        "none";
    }
    description
      "none";
  }
  augment "/ncs:devices/ncs:device/ncs:live-status/tapi-common:context/tapi-oam:oam-context/tapi-oam:meg/tapi-oam:mip" {
    container odu-mip-spec {
      tailf:ncs-device-type "netconf";
      tailf:display-when "not(../../../../../../ncs:module) or ../../../../../../ncs:module[ncs:name='tapi-odu'] or (../../../../../../ncs:live-status-protocol[not(ncs:capability)]) or (../../../../../../ncs:live-status-protocol/ncs:capability/ncs:module[.='tapi-odu'])";
      uses live_ncs_odu-mip-spec;
      description
        "none";
    }
    description
      "none";
  }
  augment "/ncs:devices/ncs:template/ncs:ned-id/ncs:config/tapi-common:context/tapi-connectivity:connectivity-context/tapi-connectivity:connectivity-service/tapi-connectivity:end-point" {
    container odu-connectivity-service-end-point-spec {
      uses ncs_template_odu-connectivity-service-end-point-spec;
      description
        "none";
    }
    description
      "none";
  }
  augment "/ncs:devices/ncs:device/ncs:live-status/tapi-common:context/tapi-connectivity:connectivity-context/tapi-connectivity:connectivity-service/tapi-connectivity:end-point" {
    container odu-connectivity-service-end-point-spec {
      tailf:ncs-device-type "netconf";
      tailf:display-when "not(../../../../../../ncs:module) or ../../../../../../ncs:module[ncs:name='tapi-odu'] or (../../../../../../ncs:live-status-protocol[not(ncs:capability)]) or (../../../../../../ncs:live-status-protocol/ncs:capability/ncs:module[.='tapi-odu'])";
      uses live_ncs_odu-connectivity-service-end-point-spec;
      description
        "none";
    }
    description
      "none";
  }
  augment "/ncs:devices/ncs:device/ncs:config/tapi-common:context/tapi-connectivity:connectivity-context/tapi-connectivity:connectivity-service/tapi-connectivity:end-point" {
    container odu-connectivity-service-end-point-spec {
      tailf:ncs-device-type "netconf";
      tailf:display-when "not(../../../../../../ncs:module) or ../../../../../../ncs:module[ncs:name='tapi-odu']";
      uses odu-connectivity-service-end-point-spec;
      description
        "none";
    }
    description
      "none";
  }

  identity ODU_TYPE_ODU_CN {
    base ODU_TYPE;
    description
      "none";
  }

  identity ODU_TYPE_ODU_FLEX {
    base ODU_TYPE;
    description
      "none";
  }

  identity ODU_TYPE_ODU4 {
    base ODU_TYPE;
    description
      "none";
  }

  identity ODU_TYPE_ODU3 {
    base ODU_TYPE;
    description
      "none";
  }

  identity ODU_TYPE_ODU2E {
    base ODU_TYPE;
    description
      "none";
  }

  identity ODU_TYPE_ODU2 {
    base ODU_TYPE;
    description
      "none";
  }

  identity ODU_TYPE_ODU1 {
    base ODU_TYPE;
    description
      "none";
  }

  identity ODU_TYPE_ODU0 {
    base ODU_TYPE;
    description
      "none";
  }

  identity ODU_TYPE {
    base tapi-common:LAYER_PROTOCOL_QUALIFIER;
    description
      "none";
  }
}
