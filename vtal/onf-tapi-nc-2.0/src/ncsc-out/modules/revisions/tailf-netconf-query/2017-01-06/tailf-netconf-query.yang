module tailf-netconf-query {
  // Generated by yanger -t ncs
  tailf:mount-id "onf-tapi-nc-2.0:onf-tapi-nc-2.0";
  tailf:ncs-device-type "netconf";

  namespace "http://tail-f.com/ns/netconf/query";
  prefix tfncq;
  // NCS drop tailf:export

  import tailf-common {
    prefix tailf;
  }
  import tailf-common-query {
    prefix tfcq;
  }
  import tailf-ncs {
    prefix ncs;
  }

  organization
    "Tail-f Systems";
  description
    "This module introduces five new rpc operations to run
     advanced search queries.

     The operation 'start-query' starts a query, with some search
     conditions and control parameters for how to return the results.
     This operation returns a query handle, to be used in subsequent
     operations.

     The operation 'fetch-query-result' is repeatedly to get result
     chunks from the query evaluation.

     The operation 'immediate-query' is used to start a new query, and return
     the entire result.

     The operation 'reset-query' can be used to restart the query.

     Finally 'stop-query' is used to clean up query resources on the
     server.

     Copyright 2014-2017 Cisco Systems, Inc.
     All rights reserved.
     Permission is hereby granted to redistribute this file without
     modification.";

  revision 2017-01-06 {
    description
      "Released as part of ConfD-6.5.2.1 / NCS-4.5.3.

       Added 'immediate-query' function.";
  }
  revision 2014-11-13 {
    description
      "Initial revision.";
  }

  augment "/ncs:devices/ncs:device/ncs:rpc" {
    container rpc-stop-query {
      tailf:ncs-device-type "netconf";
      tailf:display-when "not(../../ncs:module) or ../../ncs:module[ncs:name='tailf-netconf-query']";
      tailf:action stop-query {
        tailf:actionpoint ncsproxy {
          tailf:internal;
        }
        input {
          uses tfcq:ncs_rpc_notif_query-handle;
        }
      }
    }
  }
  augment "/ncs:devices/ncs:device-group/ncs:ned-id/ncs:rpc" {
    container rpc-stop-query {
      tailf:ncs-device-type "netconf";
      tailf:display-when "../../ncs:id = 'onf-tapi-nc-2.0:onf-tapi-nc-2.0'";
      tailf:action stop-query {
        tailf:actionpoint ncsproxy {
          tailf:internal;
        }
        input {
          uses tfcq:ncs_rpc_notif_query-handle;
        }
      }
    }
  }
  augment "/ncs:devices/ncs:device/ncs:rpc" {
    container rpc-reset-query {
      tailf:ncs-device-type "netconf";
      tailf:display-when "not(../../ncs:module) or ../../ncs:module[ncs:name='tailf-netconf-query']";
      tailf:action reset-query {
        tailf:actionpoint ncsproxy {
          tailf:internal;
        }
        input {
          uses tfcq:ncs_rpc_notif_reset-query-parameters;
        }
      }
    }
  }
  augment "/ncs:devices/ncs:device-group/ncs:ned-id/ncs:rpc" {
    container rpc-reset-query {
      tailf:ncs-device-type "netconf";
      tailf:display-when "../../ncs:id = 'onf-tapi-nc-2.0:onf-tapi-nc-2.0'";
      tailf:action reset-query {
        tailf:actionpoint ncsproxy {
          tailf:internal;
        }
        input {
          uses tfcq:ncs_rpc_notif_reset-query-parameters;
        }
      }
    }
  }
  augment "/ncs:devices/ncs:device/ncs:rpc" {
    container rpc-immediate-query {
      tailf:ncs-device-type "netconf";
      tailf:display-when "not(../../ncs:module) or ../../ncs:module[ncs:name='tailf-netconf-query']";
      tailf:action immediate-query {
        tailf:actionpoint ncsproxy {
          tailf:internal;
        }
        input {
          uses tfcq:ncs_rpc_notif_start-query-parameters;
        }
        output {
          container query-result {
            uses tfcq:ncs_rpc_notif_query-result;
          }
        }
      }
    }
  }
  augment "/ncs:devices/ncs:device-group/ncs:ned-id/ncs:rpc" {
    container rpc-immediate-query {
      tailf:ncs-device-type "netconf";
      tailf:display-when "../../ncs:id = 'onf-tapi-nc-2.0:onf-tapi-nc-2.0'";
      tailf:action immediate-query {
        tailf:actionpoint ncsproxy {
          tailf:internal;
        }
        input {
          uses tfcq:ncs_rpc_notif_start-query-parameters;
        }
        output {
          container "device" {
            leaf "name" {
              type string;
            }
            leaf "info" {
              type string;
            }
            container "result" {
              container query-result {
                uses tfcq:ncs_rpc_notif_query-result;
              }
            }
          }
        }
      }
    }
  }
  augment "/ncs:devices/ncs:device/ncs:rpc" {
    container rpc-fetch-query-result {
      tailf:ncs-device-type "netconf";
      tailf:display-when "not(../../ncs:module) or ../../ncs:module[ncs:name='tailf-netconf-query']";
      tailf:action fetch-query-result {
        tailf:actionpoint ncsproxy {
          tailf:internal;
        }
        input {
          uses tfcq:ncs_rpc_notif_query-handle;
        }
        output {
          container query-result {
            uses tfcq:ncs_rpc_notif_query-result;
          }
        }
      }
    }
  }
  augment "/ncs:devices/ncs:device-group/ncs:ned-id/ncs:rpc" {
    container rpc-fetch-query-result {
      tailf:ncs-device-type "netconf";
      tailf:display-when "../../ncs:id = 'onf-tapi-nc-2.0:onf-tapi-nc-2.0'";
      tailf:action fetch-query-result {
        tailf:actionpoint ncsproxy {
          tailf:internal;
        }
        input {
          uses tfcq:ncs_rpc_notif_query-handle;
        }
        output {
          container "device" {
            leaf "name" {
              type string;
            }
            leaf "info" {
              type string;
            }
            container "result" {
              container query-result {
                uses tfcq:ncs_rpc_notif_query-result;
              }
            }
          }
        }
      }
    }
  }
  augment "/ncs:devices/ncs:device/ncs:rpc" {
    container rpc-start-query {
      tailf:ncs-device-type "netconf";
      tailf:display-when "not(../../ncs:module) or ../../ncs:module[ncs:name='tailf-netconf-query']";
      tailf:action start-query {
        tailf:actionpoint ncsproxy {
          tailf:internal;
        }
        input {
          uses tfcq:ncs_rpc_notif_start-query-parameters;
        }
        output {
          uses tfcq:ncs_rpc_notif_query-handle;
        }
      }
    }
  }
  augment "/ncs:devices/ncs:device-group/ncs:ned-id/ncs:rpc" {
    container rpc-start-query {
      tailf:ncs-device-type "netconf";
      tailf:display-when "../../ncs:id = 'onf-tapi-nc-2.0:onf-tapi-nc-2.0'";
      tailf:action start-query {
        tailf:actionpoint ncsproxy {
          tailf:internal;
        }
        input {
          uses tfcq:ncs_rpc_notif_start-query-parameters;
        }
        output {
          container "device" {
            leaf "name" {
              type string;
            }
            leaf "info" {
              type string;
            }
            container "result" {
              uses tfcq:ncs_rpc_notif_query-handle;
            }
          }
        }
      }
    }
  }
}
