module tapi-equipment {
  // Generated by yanger -t ncs
  tailf:mount-id "onf-tapi-nc-2.0:onf-tapi-nc-2.0";
  tailf:ncs-device-type "netconf";

  namespace "urn:onf:otcc:yang:tapi-equipment";
  prefix tapi-equipment;

  import tapi-common {
    prefix tapi-common;
  }
  import tapi-topology {
    prefix tapi-topology;
  }
  import tailf-common {
    prefix tailf;
  }
  import tailf-ncs {
    prefix ncs;
  }

  organization
    "ONF OTCC (Open Transport Configuration & Control) Project";
  contact
    "
     Project Web: <https://urldefense.com/v3/__https://wiki.opennetworking.org/display/OTCC/TAPI__;!!OSsGDw!d_dJlNtYLmD585It0DKukzB2TS5KZqBZQ-pdI1D-6c6c5hRDotd6W87JJX8d$ >
     Project List: <mailto:transport-api@opennetworking.org>
     Editor: Karthik Sethuraman <mailto:karthik.sethuraman@necam.com>
     Andrea Mazzini <mailto:andrea.mazzini@nokia.com>
     Arturo Mayoral <mailto:arturo.mayoral@telefonica.com>
     Nigel Davis <mailto:ndavis@ciena.com>";
  description
    "
     This module contains TAPI Equipment Model definitions.
     Source: TapiEquipment.uml
     - The TAPI YANG models included in this TAPI release are a *normative* part of the TAPI SDK.
     - The YANG specifications have been generated from the corresponding UML model using the [ONF EAGLE UML2YANG mapping tool]
     <https://github.com/OpenNetworkingFoundation/EagleUmlYang>
     and further edited manually to comply with the [ONF IISOMI UML2YANG mapping guidelines]
     <https://wiki.opennetworking.org/display/OIMT/UML+-+YANG+Guidelines>
     - Status of YANG model artifacts can be determined by referring to the corresponding UML artifacts.
     As described in the UML models, some artifacts are considered *experimental*, and thus the corresponding YANG artifacts.
     - The ONF TAPI release process does not guarantee backward compatibility of YANG models across major versions of TAPI releases.
     The YANG model backward compatibility criteria are outlined in section 11 of <https://tools.ietf.org/html/rfc7950>.
     YANG models included in this release may not be backward compatible with previous TAPI releases.
     Copyright (c) 2018 Open Networking Foundation (ONF). All rights reserved.
     License: This module is distributed under the Apache License 2.0.";

  revision 2020-04-23 {
    description
      "ONF Transport API version 2.1.3.
       Changes included in this TAPI release (v2.1.3) are listed in
       <https://github.com/OpenNetworkingFoundation/TAPI/blob/develop_v2_1/CHANGE_LOG/change-log.2.1.3.md>";
    reference
      "ONF-TR-527, ONF-TR-512, ONF-TR-531, RFC 7950, RFC 6087 and ONF TAPI UML model
       <https://github.com/OpenNetworkingFoundation/TAPI/tree/v2.1.0/UML>";
  }
  revision 2019-07-16 {
    description
      "ONF Transport API version 2.1.2.
       Changes included in this TAPI release (v2.1.2) are listed in
       <https://github.com/OpenNetworkingFoundation/TAPI/blob/develop_v2_1/CHANGE_LOG/change-log.2.1.2.md>";
    reference
      "ONF-TR-527, ONF-TR-512, ONF-TR-531, RFC 7950, RFC 6087 and ONF TAPI UML model
       <https://github.com/OpenNetworkingFoundation/TAPI/tree/v2.1.0/UML>";
  }
  revision 2018-12-10 {
    description
      "ONF Transport API version 2.1.1.
       Changes included in this TAPI release (v2.1.1) are listed in
       <https://github.com/OpenNetworkingFoundation/TAPI/blob/develop/CHANGE_LOG/change-log.2.1.1.md>";
    reference
      "ONF-TR-527, ONF-TR-512, ONF-TR-531, RFC 7950, RFC 6087 and ONF TAPI UML model
       <https://github.com/OpenNetworkingFoundation/TAPI/tree/v2.1.0/UML>";
  }
  revision 2018-10-16 {
    description
      "ONF Transport API version 2.1.0.
       Changes included in this TAPI release (v2.1.0) are listed in
       <https://github.com/OpenNetworkingFoundation/TAPI/blob/develop/CHANGE_LOG/change-log.2.1.0.md>";
    reference
      "ONF-TR-527, ONF-TR-512, ONF-TR-531, RFC 7950, RFC 6087 and ONF TAPI UML model
       <https://github.com/OpenNetworkingFoundation/TAPI/tree/v2.1.0/UML>";
  }
  revision 2018-03-07 {
    description
      "ONF Transport API version 2.0.2
       This YANG module has been generated from the TAPI UML Model using the IISOMI-Eagle xmi2yang mapping tool.
       Changes in this revision: <https://github.com/OpenNetworkingFoundation/TAPI/blob/develop/CHANGE_LOG/change-log.2.0.2.md>";
    reference
      "ONF-TR-527, ONF-TR-512, ONF-TR-531, RFC 6020, RFC 6087 and ONF TAPI UML model
       <https://github.com/OpenNetworkingFoundation/TAPI/tree/v2.0.2/UML>";
  }
  revision 2018-02-16 {
    description
      "ONF Transport API version 2.0.1
       This YANG module has been generated from the TAPI UML Model using the IISOMI-Eagle xmi2yang mapping tool.
       Changes in this revision: <https://github.com/OpenNetworkingFoundation/TAPI/blob/develop/CHANGE_LOG/change-log.2.0.1.md>";
    reference
      "ONF-TR-527, ONF-TR-512, ONF-TR-531, RFC 6020, RFC 6087 and ONF TAPI UML model
       <https://github.com/OpenNetworkingFoundation/TAPI/tree/v2.0.1/UML>";
  }
  revision 2018-01-02 {
    description
      "ONF Transport API version 2.0.0
       This YANG module has been generated from the TAPI UML Model using the IISOMI-Eagle xmi2yang mapping tool.
       Changes in this revision: <https://github.com/OpenNetworkingFoundation/TAPI/blob/develop/CHANGE_LOG/change-log.2.0.0.md>";
    reference
      "ONF-TR-527, ONF-TR-512, ONF-TR-531, RFC 6020, RFC 6087 and ONF TAPI UML model
       <https://github.com/OpenNetworkingFoundation/TAPI/tree/v2.0.0/UML>";
  }

  typedef ncs_template_connector-and-pin-orientation {
    type string;
    description
      "Most connector schemes are asymmetric such that there are two orientations of the connector where a mating is only possible between two connectors of different orientations.
       A multi-pin connector may have a mix of pin orientations. In this case, it is expected that the dominant orientation of pin is chosen for the connector orientation.";
  }

  typedef ncs_template_equipment-category {
    type string;
    description
      "The form of equipment.";
  }

  typedef ncs_template_holder-category {
    type string;
    description
      "The form of holder.";
  }

  typedef ncs_template_equipment-object-type {
    type string;
    description
      "The list of TAPI Equipment Object types/classes.";
  }

  typedef ncs_rpc_notif_connector-and-pin-orientation {
    type identityref {
      base CONNECTOR_AND_PIN_ORIENTATION;
    }
    description
      "Most connector schemes are asymmetric such that there are two orientations of the connector where a mating is only possible between two connectors of different orientations.
       A multi-pin connector may have a mix of pin orientations. In this case, it is expected that the dominant orientation of pin is chosen for the connector orientation.";
  }

  typedef ncs_rpc_notif_equipment-category {
    type identityref {
      base EQUIPMENT_CATEGORY;
    }
    description
      "The form of equipment.";
  }

  typedef ncs_rpc_notif_holder-category {
    type identityref {
      base HOLDER_CATEGORY;
    }
    description
      "The form of holder.";
  }

  typedef ncs_rpc_notif_equipment-object-type {
    type identityref {
      base EQUIPMENT_OBJECT_TYPE;
    }
    description
      "The list of TAPI Equipment Object types/classes.";
  }

  typedef live_ncs_connector-and-pin-orientation {
    type identityref {
      base CONNECTOR_AND_PIN_ORIENTATION;
    }
    description
      "Most connector schemes are asymmetric such that there are two orientations of the connector where a mating is only possible between two connectors of different orientations.
       A multi-pin connector may have a mix of pin orientations. In this case, it is expected that the dominant orientation of pin is chosen for the connector orientation.";
  }

  typedef live_ncs_equipment-category {
    type identityref {
      base EQUIPMENT_CATEGORY;
    }
    description
      "The form of equipment.";
  }

  typedef live_ncs_holder-category {
    type identityref {
      base HOLDER_CATEGORY;
    }
    description
      "The form of holder.";
  }

  typedef live_ncs_equipment-object-type {
    type identityref {
      base EQUIPMENT_OBJECT_TYPE;
    }
    description
      "The list of TAPI Equipment Object types/classes.";
  }

  typedef connector-and-pin-orientation {
    type identityref {
      base CONNECTOR_AND_PIN_ORIENTATION;
    }
    description
      "Most connector schemes are asymmetric such that there are two orientations of the connector where a mating is only possible between two connectors of different orientations.
       A multi-pin connector may have a mix of pin orientations. In this case, it is expected that the dominant orientation of pin is chosen for the connector orientation.";
  }

  typedef equipment-category {
    type identityref {
      base EQUIPMENT_CATEGORY;
    }
    description
      "The form of equipment.";
  }

  typedef holder-category {
    type identityref {
      base HOLDER_CATEGORY;
    }
    description
      "The form of holder.";
  }

  typedef equipment-object-type {
    type identityref {
      base EQUIPMENT_OBJECT_TYPE;
    }
    description
      "The list of TAPI Equipment Object types/classes.";
  }

  grouping ncs_template_device-ref {
    leaf device-uuid {
      type string;
      description
        "none";
    }
    description
      "none";
  }

  grouping ncs_template_equipment-ref {
    uses ncs_template_device-ref;
    leaf equipment-uuid {
      type string;
      description
        "none";
    }
    description
      "none";
  }

  grouping ncs_template_equipment-holder-ref {
    uses ncs_template_equipment-ref;
    leaf equipment-holder-uuid {
      type string;
      description
        "none";
    }
    description
      "none";
  }

  grouping ncs_template_access-port-ref {
    uses ncs_template_device-ref;
    leaf access-port-uuid {
      type string;
      description
        "none";
    }
    description
      "none";
  }

  grouping ncs_template_physical-span-ref {
    leaf physical-span-uuid {
      type string;
      description
        "none";
    }
    description
      "none";
  }

  grouping ncs_template_abstract-strand-ref {
    uses ncs_template_physical-span-ref;
    leaf abstract-strand-local-id {
      type string;
      description
        "none";
    }
    description
      "none";
  }

  grouping ncs_template_connector-pin-address {
    leaf connector-identification {
      type string;
      description
        "Identification of the Connector in the context of the referenced Equipment.";
    }
    leaf pin-identification {
      type string;
      description
        "Where relevant, identification of the Pin in the context of the connector.
         Where the whole connector is used, then individual Pins need not be identified.
         Simple alternative to pinAndRole.";
    }
    leaf equipment-uuid {
      type tapi-common:ncs_template_uuid;
      description
        "Reference to the Equipment that is fitted with the Connector/Pin.";
    }
    // NCS drop config false list 'pin-and-role'
    description
      "The identification of the location of the Connector and/or Pin.";
  }

  grouping ncs_template_actual-equipment {
    // NCS drop config false list 'actual-non-field-replaceable-module'
    // NCS drop config false container 'common-actual-properties'
    // NCS drop config false container 'common-equipment-properties'
    description
      "The equipment that is actually present in the physical network.
       It will expose all dynamic properties and some critical static properties.";
  }

  grouping ncs_template_actual-holder {
    // NCS drop config false container 'common-holder-properties'
    description
      "A holder in the ActualEquipment.";
  }

  grouping ncs_template_actual-non-field-replaceable-module {
    // NCS drop config false container 'common-actual-properties'
    // NCS drop config false container 'common-equipment-properties'
    description
      "A structure that represents an actual equipment that cannot be replaced in the field.
       Is simply a subordinate part of an ActualEquipment (FRU).
       Does not have any exposed holders (any associated holders are assumed to belong to the containing FRU).
       Does not have any connectors (any associated connectors are assumed to belong to the containing FRU).
      ";
  }

  grouping ncs_template_common-actual-properties {
    leaf asset-instance-identifier {
      type string;
      description
        "This attribute represents the asset identifier of this instance from the manufacturer's perspective.";
    }
    leaf is-powered {
      type string;
      description
        "The state of the power being supplied to the equipment.
         Note that this attribute summarizes the power state.
         Full details on the actual power system would be provided from a number of PC instances representing the relevant parts of the Power function (e.g. different voltage supplies).";
    }
    leaf manufacture-date {
      type tapi-common:ncs_template_date-and-time;
      description
        "This attribute represents the date on which this instance is manufactured.";
    }
    leaf serial-number {
      type string;
      description
        "This attribute represents the serial number of this instance.";
    }
    leaf temperature {
      type string;
      description
        "The measured temperature of the Equipment.";
    }
    description
      "Properties common to actual Equipment.";
  }

  grouping ncs_template_common-equipment-properties {
    leaf asset-type-identifier {
      type string;
      description
        "Represents the invariant properties of the equipment asset allocated by the operator that define and characterize the type.";
    }
    leaf equipment-type-description {
      type string;
      description
        "Text describing the type of Equipment.";
    }
    leaf equipment-type-identifier {
      type string;
      description
        "This attribute identifies the part type of the equipment.";
    }
    leaf equipment-type-name {
      type string;
      description
        "This attribute identifies the type of the equipment.";
    }
    leaf equipment-type-version {
      type string;
      description
        "This attribute identifies the version of the equipment.";
    }
    leaf manufacturer-identifier {
      type string;
      description
        "The formal unique identifier of the manufacturer.";
    }
    leaf manufacturer-name {
      type string;
      description
        "The formal name of the manufacturer of the Equipment.";
    }
    description
      "Properties common to all aspects of Equipment.";
  }

  grouping ncs_template_common-holder-properties {
    leaf holder-category {
      type ncs_template_holder-category;
      description
        "The type of holder.";
    }
    leaf is-guided {
      type string;
      description
        "This attribute indicates whether the holder has guides that constrain the position of the equipment in the holder or not.";
    }
    leaf holder-location {
      type string;
      description
        "The relative position of the holder in the context of its containing equipment along with the position of that containing Equipment (and further recursion).";
    }
    description
      "Properties common to all aspects of Holder.";
  }

  grouping ncs_template_expected-equipment {
    // NCS drop config false list 'expected-non-field-replaceable-module'
    // NCS drop config false list 'expected-holder'
    // NCS drop config false container 'common-equipment-properties'
    description
      "A definition of the restrictions on the equipment that is expected to be present in the physical network at a particular 'place'.
       The expected equipment will state the type and may constrain any other invariant properties.
       It may also provide desired ranges for dynamic properties.";
  }

  grouping ncs_template_expected-holder {
    // NCS drop config false container 'common-holder-properties'
    description
      "A definition of a holder expected in the ActualEquipment (i.e. an ActualHolder) as part of the constraints provided by the ExpectedEquipment.";
  }

  grouping ncs_template_expected-non-field-replaceable-module {
    // NCS drop config false container 'common-equipment-properties'
    description
      "A structure that represents an expected equipment that cannot be replaced in the field.
       Is simply a subordinate part of an ExpectedEquipment (FRU).
       Does not have any exposed holders (any associated holders are assumed to belong to the containing FRU).
       Does not have any connectors (any associated connectors are assumed to belong to the containing FRU).
      ";
  }

  grouping ncs_template_pin-and-role {
    // NCS drop config false leaf 'location-in-connector'
    // NCS drop config false leaf-list 'pin-role'
    // NCS drop config false leaf 'pin-name'
    description
      "Provides an opportunity, for a pin, to give the location of the pin and the role of the pin.";
  }

  grouping ncs_template_equipment {
    // NCS drop config false list 'contained-holder'
    // NCS drop config false leaf category
    // NCS drop config false leaf 'equipment-location'
    // NCS drop config false leaf 'geographical-location'
    // NCS drop config false leaf 'is-expected-actual-mismatch'
    list expected-equipment {
      // NCS patched for predictable order
      ordered-by user;
      uses ncs_template_expected-equipment;
      description
        "none";
    }
    container actual-equipment {
      uses ncs_template_actual-equipment;
      description
        "none";
    }
    uses tapi-common:ncs_template_global-class;
    description
      "Represents any relevant physical thing.
       Can be either field replaceable or not field replaceable.
       Note: The model is currently constrained to inside plant.";
  }

  grouping ncs_template_holder {
    // NCS drop config false container 'occupying-fru'
    // NCS drop config false container 'expected-holder'
    // NCS drop config false container 'actual-holder'
    uses tapi-common:ncs_template_global-class;
    description
      "Represents a space in an equipment in which another equipment can be fitted in the field.";
  }

  grouping ncs_template_access-port {
    // NCS drop config false list 'connector-pin'
    uses tapi-common:ncs_template_global-class;
    description
      "A group of pins that together support a signal group where any one pin removed from the group will prevent all signals of the signal group from flowing successfully.
       In some cases the AccessPort may simply reference a single connector (e.g., where the pin-connector association is simpe such that the AccessPort references all pinsof one connector).";
  }

  grouping ncs_template_physical-span {
    // NCS drop config false list 'access-port'
    // NCS drop config false list 'abstract-strand'
    uses tapi-common:ncs_template_global-class;
    description
      "An adjacency between AccessPorts.
       The adjacency is supported by a group of strands between pins of the AccessPorts.
       This is a physical abstraction.";
  }

  grouping ncs_template_abstract-strand {
    // NCS drop config false list 'adjacent-strand'
    // NCS drop config false list 'spliced-strand'
    // NCS drop config false list 'connector-pin'
    // NCS drop config false list 'strand-media-characteristics'
    uses tapi-common:ncs_template_local-class;
    description
      "This object represents an abstraction of one or more strands in series that provides sufficient detail to enable appropriate engineering.
       A strand represents a continuous long, thin piece of a medium such as glass fiber or copper wire.
       In this model a Strand:
       - a strand has two ends
       - a splice can only be between 2 strands.
       - the end of a strand may have a splice, a connector or be hidden
       - only one end can be hidden in an equipment
       - where a cable has more than two end each strand only goes between two of the ends
       This model does NOT account for multiple copper strands being spliced.";
  }

  grouping ncs_template_device {
    // NCS drop config false list equipment
    // NCS drop config false list 'access-port'
    uses tapi-common:ncs_template_global-class;
    description
      "A logical grouping of Equipments and AccessPorts that are closely located and form a support a coherent system of related functions.";
  }

  grouping ncs_template_physical-context {
    // NCS drop config false list device
    // NCS drop config false list 'physical-span'
    uses tapi-common:ncs_template_global-class;
    description
      "none";
  }

  grouping ncs_template_supporting-physical-span {
    container physical-span {
      uses ncs_template_physical-span-ref;
      description
        "none";
    }
    description
      "none";
  }

  grouping ncs_template_supporting-access-port {
    container access-port {
      uses ncs_template_access-port-ref;
      description
        "none";
    }
    description
      "none";
  }

  grouping ncs_rpc_notif_device-ref {
    leaf device-uuid {
      type string;
      description
        "none";
    }
    description
      "none";
  }

  grouping ncs_rpc_notif_equipment-ref {
    uses ncs_rpc_notif_device-ref;
    leaf equipment-uuid {
      type string;
      description
        "none";
    }
    description
      "none";
  }

  grouping ncs_rpc_notif_equipment-holder-ref {
    uses ncs_rpc_notif_equipment-ref;
    leaf equipment-holder-uuid {
      type string;
      description
        "none";
    }
    description
      "none";
  }

  grouping ncs_rpc_notif_access-port-ref {
    uses ncs_rpc_notif_device-ref;
    leaf access-port-uuid {
      type string;
      description
        "none";
    }
    description
      "none";
  }

  grouping ncs_rpc_notif_physical-span-ref {
    leaf physical-span-uuid {
      type string;
      description
        "none";
    }
    description
      "none";
  }

  grouping ncs_rpc_notif_abstract-strand-ref {
    uses ncs_rpc_notif_physical-span-ref;
    leaf abstract-strand-local-id {
      type string;
      description
        "none";
    }
    description
      "none";
  }

  grouping ncs_rpc_notif_connector-pin-address {
    leaf connector-identification {
      type string;
      description
        "Identification of the Connector in the context of the referenced Equipment.";
    }
    leaf pin-identification {
      type string;
      description
        "Where relevant, identification of the Pin in the context of the connector.
         Where the whole connector is used, then individual Pins need not be identified.
         Simple alternative to pinAndRole.";
    }
    leaf equipment-uuid {
      type tapi-common:ncs_rpc_notif_uuid;
      description
        "Reference to the Equipment that is fitted with the Connector/Pin.";
    }
    list pin-and-role {
      config false;
      uses ncs_rpc_notif_pin-and-role;
      description
        "If there is more than one pin used in a connector and/or there is a need to identify the role of one or more pins then this property can be used.
         For simple cases pinIdentification can be used instead.";
    }
    description
      "The identification of the location of the Connector and/or Pin.";
  }

  grouping ncs_rpc_notif_actual-equipment {
    list actual-non-field-replaceable-module {
      config false;
      uses ncs_rpc_notif_actual-non-field-replaceable-module;
      description
        "none";
    }
    container common-actual-properties {
      config false;
      uses ncs_rpc_notif_common-actual-properties;
      description
        "none";
    }
    container common-equipment-properties {
      config false;
      uses ncs_rpc_notif_common-equipment-properties;
      description
        "none";
    }
    description
      "The equipment that is actually present in the physical network.
       It will expose all dynamic properties and some critical static properties.";
  }

  grouping ncs_rpc_notif_actual-holder {
    container common-holder-properties {
      config false;
      uses ncs_rpc_notif_common-holder-properties;
      description
        "none";
    }
    description
      "A holder in the ActualEquipment.";
  }

  grouping ncs_rpc_notif_actual-non-field-replaceable-module {
    container common-actual-properties {
      config false;
      uses ncs_rpc_notif_common-actual-properties;
      description
        "none";
    }
    container common-equipment-properties {
      config false;
      uses ncs_rpc_notif_common-equipment-properties;
      description
        "none";
    }
    description
      "A structure that represents an actual equipment that cannot be replaced in the field.
       Is simply a subordinate part of an ActualEquipment (FRU).
       Does not have any exposed holders (any associated holders are assumed to belong to the containing FRU).
       Does not have any connectors (any associated connectors are assumed to belong to the containing FRU).
      ";
  }

  grouping ncs_rpc_notif_common-actual-properties {
    leaf asset-instance-identifier {
      type string;
      description
        "This attribute represents the asset identifier of this instance from the manufacturer's perspective.";
    }
    leaf is-powered {
      type boolean;
      description
        "The state of the power being supplied to the equipment.
         Note that this attribute summarizes the power state.
         Full details on the actual power system would be provided from a number of PC instances representing the relevant parts of the Power function (e.g. different voltage supplies).";
    }
    leaf manufacture-date {
      type tapi-common:ncs_rpc_notif_date-and-time;
      description
        "This attribute represents the date on which this instance is manufactured.";
    }
    leaf serial-number {
      type string;
      description
        "This attribute represents the serial number of this instance.";
    }
    leaf temperature {
      type decimal64 {
        fraction-digits 7;
      }
      description
        "The measured temperature of the Equipment.";
    }
    description
      "Properties common to actual Equipment.";
  }

  grouping ncs_rpc_notif_common-equipment-properties {
    leaf asset-type-identifier {
      type string;
      description
        "Represents the invariant properties of the equipment asset allocated by the operator that define and characterize the type.";
    }
    leaf equipment-type-description {
      type string;
      description
        "Text describing the type of Equipment.";
    }
    leaf equipment-type-identifier {
      type string;
      description
        "This attribute identifies the part type of the equipment.";
    }
    leaf equipment-type-name {
      type string;
      description
        "This attribute identifies the type of the equipment.";
    }
    leaf equipment-type-version {
      type string;
      description
        "This attribute identifies the version of the equipment.";
    }
    leaf manufacturer-identifier {
      type string;
      description
        "The formal unique identifier of the manufacturer.";
    }
    leaf manufacturer-name {
      type string;
      description
        "The formal name of the manufacturer of the Equipment.";
    }
    description
      "Properties common to all aspects of Equipment.";
  }

  grouping ncs_rpc_notif_common-holder-properties {
    leaf holder-category {
      type ncs_rpc_notif_holder-category;
      description
        "The type of holder.";
    }
    leaf is-guided {
      type boolean;
      description
        "This attribute indicates whether the holder has guides that constrain the position of the equipment in the holder or not.";
    }
    leaf holder-location {
      type string;
      description
        "The relative position of the holder in the context of its containing equipment along with the position of that containing Equipment (and further recursion).";
    }
    description
      "Properties common to all aspects of Holder.";
  }

  grouping ncs_rpc_notif_expected-equipment {
    list expected-non-field-replaceable-module {
      config false;
      uses ncs_rpc_notif_expected-non-field-replaceable-module;
      description
        "none";
    }
    list expected-holder {
      config false;
      uses ncs_rpc_notif_expected-holder;
      description
        "none";
    }
    container common-equipment-properties {
      config false;
      uses ncs_rpc_notif_common-equipment-properties;
      description
        "none";
    }
    description
      "A definition of the restrictions on the equipment that is expected to be present in the physical network at a particular 'place'.
       The expected equipment will state the type and may constrain any other invariant properties.
       It may also provide desired ranges for dynamic properties.";
  }

  grouping ncs_rpc_notif_expected-holder {
    container common-holder-properties {
      config false;
      uses ncs_rpc_notif_common-holder-properties;
      description
        "none";
    }
    description
      "A definition of a holder expected in the ActualEquipment (i.e. an ActualHolder) as part of the constraints provided by the ExpectedEquipment.";
  }

  grouping ncs_rpc_notif_expected-non-field-replaceable-module {
    container common-equipment-properties {
      config false;
      uses ncs_rpc_notif_common-equipment-properties;
      description
        "none";
    }
    description
      "A structure that represents an expected equipment that cannot be replaced in the field.
       Is simply a subordinate part of an ExpectedEquipment (FRU).
       Does not have any exposed holders (any associated holders are assumed to belong to the containing FRU).
       Does not have any connectors (any associated connectors are assumed to belong to the containing FRU).
      ";
  }

  grouping ncs_rpc_notif_pin-and-role {
    leaf location-in-connector {
      type string;
      config false;
      description
        "The named location of the pin in the context of the connector.
         This is likely to be the normal numbering/naming for the type of connetor, e.g. '7', '6-GND', 'Common' etc.";
    }
    leaf-list pin-role {
      type string;
      config false;
      description
        "It is not always necessary to specify a role (or list of roles) as the connector locationInConnector may be sufficient (as these are sometimes clearly role based.
         Each entry represents a role in the context of the specific access port.
         Each entry ties the pin to a functional element in the associated NEP(s) etc.
         For example:
         - a pin might carry several distinct signals where each signal is idenitified in the list
         - a pin may carry a signal and power
         - a signal carried by a pin may be the receive flow (INPUT) to a bidirectional NEP or the transmit flow (OUTPUT) or indeed both (BIDIRECTIONAL).";
    }
    leaf pin-name {
      type string;
      config false;
      description
        "Where the pin has a distinct location identifier and a distinct name this field can be used for the name.
         For example:
         - locationInConnector = 6, pinName = GND";
    }
    description
      "Provides an opportunity, for a pin, to give the location of the pin and the role of the pin.";
  }

  grouping ncs_rpc_notif_equipment {
    list contained-holder {
      key "uuid";
      config false;
      uses ncs_rpc_notif_holder;
      description
        "References the Holder in an Equipment that is available to take other Equipments.
         For example:
         - Slot in a sub-rack
         - Slot in a Field Replaceable Unit that can take a small form-factor pluggable.";
    }
    leaf category {
      type ncs_rpc_notif_equipment-category;
      config false;
      description
        "This attribute provides the identifier for the form of equipments regarded as having particular shared characteristics.";
    }
    leaf equipment-location {
      type string;
      config false;
      description
        "none";
    }
    leaf geographical-location {
      type string;
      config false;
      description
        "none";
    }
    leaf is-expected-actual-mismatch {
      type boolean;
      config false;
      description
        "none";
    }
    list expected-equipment {
      uses ncs_rpc_notif_expected-equipment;
      description
        "none";
    }
    container actual-equipment {
      uses ncs_rpc_notif_actual-equipment;
      description
        "none";
    }
    uses tapi-common:ncs_rpc_notif_global-class;
    description
      "Represents any relevant physical thing.
       Can be either field replaceable or not field replaceable.
       Note: The model is currently constrained to inside plant.";
  }

  grouping ncs_rpc_notif_holder {
    container occupying-fru {
      uses ncs_rpc_notif_equipment-ref;
      config false;
      description
        "The FRU that is occupying the holder.
         A holder may be unoccupied.
         An FRU may occupy more hat one holder (using or blocking are intentionally not distinguished here).";
    }
    container expected-holder {
      config false;
      uses ncs_rpc_notif_expected-holder;
      description
        "none";
    }
    container actual-holder {
      config false;
      uses ncs_rpc_notif_actual-holder;
      description
        "none";
    }
    uses tapi-common:ncs_rpc_notif_global-class;
    description
      "Represents a space in an equipment in which another equipment can be fitted in the field.";
  }

  grouping ncs_rpc_notif_access-port {
    list connector-pin {
      key "connector-identification pin-identification equipment-uuid";
      config false;
      min-elements 1;
      uses ncs_rpc_notif_connector-pin-address;
      description
        "The list of Pins that support the AccessPort.";
    }
    uses tapi-common:ncs_rpc_notif_global-class;
    description
      "A group of pins that together support a signal group where any one pin removed from the group will prevent all signals of the signal group from flowing successfully.
       In some cases the AccessPort may simply reference a single connector (e.g., where the pin-connector association is simpe such that the AccessPort references all pinsof one connector).";
  }

  grouping ncs_rpc_notif_physical-span {
    list access-port {
      uses ncs_rpc_notif_access-port-ref;
      key "device-uuid access-port-uuid";
      config false;
      min-elements 2;
      max-elements 2;
      description
        "none";
    }
    list abstract-strand {
      key "local-id";
      config false;
      uses ncs_rpc_notif_abstract-strand;
      description
        "Both the serial segments that form an end-end strand and the parallel end-end strands.";
    }
    uses tapi-common:ncs_rpc_notif_global-class;
    description
      "An adjacency between AccessPorts.
       The adjacency is supported by a group of strands between pins of the AccessPorts.
       This is a physical abstraction.";
  }

  grouping ncs_rpc_notif_abstract-strand {
    list adjacent-strand {
      uses ncs_rpc_notif_abstract-strand-ref;
      key "physical-span-uuid abstract-strand-local-id";
      config false;
      description
        "none";
    }
    list spliced-strand {
      uses ncs_rpc_notif_abstract-strand-ref;
      key "physical-span-uuid abstract-strand-local-id";
      config false;
      max-elements 2;
      description
        "none";
    }
    list connector-pin {
      key "connector-identification pin-identification equipment-uuid";
      config false;
      max-elements 2;
      uses ncs_rpc_notif_connector-pin-address;
      description
        "A strand can end on two or more Pins (usually 2 pins, but a strand my be spliced to split a signal). This model supports only 2 ended strands.
         A abstract strand may be spliced at both ends and hence have no direct relationship to pins or may be connected to pins at one or both ends.
         In the essential model these Pins would be on connectors that plug in to connectors on Equipments.
         The AbstractStrand is extended to the pins of the AccessPort which are the Pins on the Connectors of the Equipment.
         In some cases it may not be relevant to represent the pin detail and hence the reference is to a connector alone.";
    }
    list strand-media-characteristics {
      key "value-name";
      config false;
      uses tapi-common:ncs_rpc_notif_name-and-value;
      description
        "Relevant physical properties of the abstract strand.";
    }
    uses tapi-common:ncs_rpc_notif_local-class;
    description
      "This object represents an abstraction of one or more strands in series that provides sufficient detail to enable appropriate engineering.
       A strand represents a continuous long, thin piece of a medium such as glass fiber or copper wire.
       In this model a Strand:
       - a strand has two ends
       - a splice can only be between 2 strands.
       - the end of a strand may have a splice, a connector or be hidden
       - only one end can be hidden in an equipment
       - where a cable has more than two end each strand only goes between two of the ends
       This model does NOT account for multiple copper strands being spliced.";
  }

  grouping ncs_rpc_notif_device {
    list equipment {
      key "uuid";
      config false;
      uses ncs_rpc_notif_equipment;
      description
        "none";
    }
    list access-port {
      key "uuid";
      config false;
      uses ncs_rpc_notif_access-port;
      description
        "none";
    }
    uses tapi-common:ncs_rpc_notif_global-class;
    description
      "A logical grouping of Equipments and AccessPorts that are closely located and form a support a coherent system of related functions.";
  }

  grouping ncs_rpc_notif_physical-context {
    list device {
      key "uuid";
      config false;
      uses ncs_rpc_notif_device;
      description
        "none";
    }
    list physical-span {
      key "uuid";
      config false;
      uses ncs_rpc_notif_physical-span;
      description
        "none";
    }
    uses tapi-common:ncs_rpc_notif_global-class;
    description
      "none";
  }

  grouping ncs_rpc_notif_supporting-physical-span {
    container physical-span {
      uses ncs_rpc_notif_physical-span-ref;
      description
        "none";
    }
    description
      "none";
  }

  grouping ncs_rpc_notif_supporting-access-port {
    container access-port {
      uses ncs_rpc_notif_access-port-ref;
      description
        "none";
    }
    description
      "none";
  }

  grouping live_ncs_device-ref {
    leaf device-uuid {
      type leafref {
        path "/ncs:devices/ncs:device/ncs:live-status/tapi-common:context/tapi-equipment:physical-context/tapi-equipment:device/tapi-equipment:uuid" {
          tailf:xpath-root 3;
        }
      }
      description
        "none";
    }
    description
      "none";
  }

  grouping live_ncs_equipment-ref {
    uses live_ncs_device-ref;
    leaf equipment-uuid {
      type leafref {
        path "/ncs:devices/ncs:device/ncs:live-status/tapi-common:context/tapi-equipment:physical-context/tapi-equipment:device/tapi-equipment:equipment/tapi-equipment:uuid" {
          tailf:xpath-root 3;
        }
      }
      description
        "none";
    }
    description
      "none";
  }

  grouping live_ncs_equipment-holder-ref {
    uses live_ncs_equipment-ref;
    leaf equipment-holder-uuid {
      type leafref {
        path "/ncs:devices/ncs:device/ncs:live-status/tapi-common:context/tapi-equipment:physical-context/tapi-equipment:device/tapi-equipment:equipment/tapi-equipment:contained-holder/tapi-equipment:uuid" {
          tailf:xpath-root 3;
        }
      }
      description
        "none";
    }
    description
      "none";
  }

  grouping live_ncs_access-port-ref {
    uses live_ncs_device-ref;
    leaf access-port-uuid {
      type leafref {
        path "/ncs:devices/ncs:device/ncs:live-status/tapi-common:context/tapi-equipment:physical-context/tapi-equipment:device/tapi-equipment:access-port/tapi-equipment:uuid" {
          tailf:xpath-root 3;
        }
      }
      description
        "none";
    }
    description
      "none";
  }

  grouping live_ncs_physical-span-ref {
    leaf physical-span-uuid {
      type leafref {
        path "/ncs:devices/ncs:device/ncs:live-status/tapi-common:context/tapi-equipment:physical-context/tapi-equipment:physical-span/tapi-equipment:uuid" {
          tailf:xpath-root 3;
        }
      }
      description
        "none";
    }
    description
      "none";
  }

  grouping live_ncs_abstract-strand-ref {
    uses live_ncs_physical-span-ref;
    leaf abstract-strand-local-id {
      type leafref {
        path "/ncs:devices/ncs:device/ncs:live-status/tapi-common:context/tapi-equipment:physical-context/tapi-equipment:physical-span/tapi-equipment:abstract-strand/tapi-equipment:local-id" {
          tailf:xpath-root 3;
        }
      }
      description
        "none";
    }
    description
      "none";
  }

  grouping live_ncs_connector-pin-address {
    leaf connector-identification {
      type string;
      description
        "Identification of the Connector in the context of the referenced Equipment.";
    }
    leaf pin-identification {
      type string;
      description
        "Where relevant, identification of the Pin in the context of the connector.
         Where the whole connector is used, then individual Pins need not be identified.
         Simple alternative to pinAndRole.";
    }
    leaf equipment-uuid {
      type tapi-common:live_ncs_uuid;
      description
        "Reference to the Equipment that is fitted with the Connector/Pin.";
    }
    list pin-and-role {
      uses live_ncs_pin-and-role;
      description
        "If there is more than one pin used in a connector and/or there is a need to identify the role of one or more pins then this property can be used.
         For simple cases pinIdentification can be used instead.";
    }
    description
      "The identification of the location of the Connector and/or Pin.";
  }

  grouping live_ncs_actual-equipment {
    list actual-non-field-replaceable-module {
      uses live_ncs_actual-non-field-replaceable-module;
      description
        "none";
    }
    container common-actual-properties {
      uses live_ncs_common-actual-properties;
      description
        "none";
    }
    container common-equipment-properties {
      uses live_ncs_common-equipment-properties;
      description
        "none";
    }
    description
      "The equipment that is actually present in the physical network.
       It will expose all dynamic properties and some critical static properties.";
  }

  grouping live_ncs_actual-holder {
    container common-holder-properties {
      uses live_ncs_common-holder-properties;
      description
        "none";
    }
    description
      "A holder in the ActualEquipment.";
  }

  grouping live_ncs_actual-non-field-replaceable-module {
    container common-actual-properties {
      uses live_ncs_common-actual-properties;
      description
        "none";
    }
    container common-equipment-properties {
      uses live_ncs_common-equipment-properties;
      description
        "none";
    }
    description
      "A structure that represents an actual equipment that cannot be replaced in the field.
       Is simply a subordinate part of an ActualEquipment (FRU).
       Does not have any exposed holders (any associated holders are assumed to belong to the containing FRU).
       Does not have any connectors (any associated connectors are assumed to belong to the containing FRU).
      ";
  }

  grouping live_ncs_common-actual-properties {
    leaf asset-instance-identifier {
      type string;
      description
        "This attribute represents the asset identifier of this instance from the manufacturer's perspective.";
    }
    leaf is-powered {
      type boolean;
      description
        "The state of the power being supplied to the equipment.
         Note that this attribute summarizes the power state.
         Full details on the actual power system would be provided from a number of PC instances representing the relevant parts of the Power function (e.g. different voltage supplies).";
    }
    leaf manufacture-date {
      type tapi-common:live_ncs_date-and-time;
      description
        "This attribute represents the date on which this instance is manufactured.";
    }
    leaf serial-number {
      type string;
      description
        "This attribute represents the serial number of this instance.";
    }
    leaf temperature {
      type decimal64 {
        fraction-digits 7;
      }
      description
        "The measured temperature of the Equipment.";
    }
    description
      "Properties common to actual Equipment.";
  }

  grouping live_ncs_common-equipment-properties {
    leaf asset-type-identifier {
      type string;
      description
        "Represents the invariant properties of the equipment asset allocated by the operator that define and characterize the type.";
    }
    leaf equipment-type-description {
      type string;
      description
        "Text describing the type of Equipment.";
    }
    leaf equipment-type-identifier {
      type string;
      description
        "This attribute identifies the part type of the equipment.";
    }
    leaf equipment-type-name {
      type string;
      description
        "This attribute identifies the type of the equipment.";
    }
    leaf equipment-type-version {
      type string;
      description
        "This attribute identifies the version of the equipment.";
    }
    leaf manufacturer-identifier {
      type string;
      description
        "The formal unique identifier of the manufacturer.";
    }
    leaf manufacturer-name {
      type string;
      description
        "The formal name of the manufacturer of the Equipment.";
    }
    description
      "Properties common to all aspects of Equipment.";
  }

  grouping live_ncs_common-holder-properties {
    leaf holder-category {
      type live_ncs_holder-category;
      description
        "The type of holder.";
    }
    leaf is-guided {
      type boolean;
      description
        "This attribute indicates whether the holder has guides that constrain the position of the equipment in the holder or not.";
    }
    leaf holder-location {
      type string;
      description
        "The relative position of the holder in the context of its containing equipment along with the position of that containing Equipment (and further recursion).";
    }
    description
      "Properties common to all aspects of Holder.";
  }

  grouping live_ncs_expected-equipment {
    list expected-non-field-replaceable-module {
      uses live_ncs_expected-non-field-replaceable-module;
      description
        "none";
    }
    list expected-holder {
      uses live_ncs_expected-holder;
      description
        "none";
    }
    container common-equipment-properties {
      uses live_ncs_common-equipment-properties;
      description
        "none";
    }
    description
      "A definition of the restrictions on the equipment that is expected to be present in the physical network at a particular 'place'.
       The expected equipment will state the type and may constrain any other invariant properties.
       It may also provide desired ranges for dynamic properties.";
  }

  grouping live_ncs_expected-holder {
    container common-holder-properties {
      uses live_ncs_common-holder-properties;
      description
        "none";
    }
    description
      "A definition of a holder expected in the ActualEquipment (i.e. an ActualHolder) as part of the constraints provided by the ExpectedEquipment.";
  }

  grouping live_ncs_expected-non-field-replaceable-module {
    container common-equipment-properties {
      uses live_ncs_common-equipment-properties;
      description
        "none";
    }
    description
      "A structure that represents an expected equipment that cannot be replaced in the field.
       Is simply a subordinate part of an ExpectedEquipment (FRU).
       Does not have any exposed holders (any associated holders are assumed to belong to the containing FRU).
       Does not have any connectors (any associated connectors are assumed to belong to the containing FRU).
      ";
  }

  grouping live_ncs_pin-and-role {
    leaf location-in-connector {
      type string;
      description
        "The named location of the pin in the context of the connector.
         This is likely to be the normal numbering/naming for the type of connetor, e.g. '7', '6-GND', 'Common' etc.";
    }
    leaf-list pin-role {
      type string;
      description
        "It is not always necessary to specify a role (or list of roles) as the connector locationInConnector may be sufficient (as these are sometimes clearly role based.
         Each entry represents a role in the context of the specific access port.
         Each entry ties the pin to a functional element in the associated NEP(s) etc.
         For example:
         - a pin might carry several distinct signals where each signal is idenitified in the list
         - a pin may carry a signal and power
         - a signal carried by a pin may be the receive flow (INPUT) to a bidirectional NEP or the transmit flow (OUTPUT) or indeed both (BIDIRECTIONAL).";
    }
    leaf pin-name {
      type string;
      description
        "Where the pin has a distinct location identifier and a distinct name this field can be used for the name.
         For example:
         - locationInConnector = 6, pinName = GND";
    }
    description
      "Provides an opportunity, for a pin, to give the location of the pin and the role of the pin.";
  }

  grouping live_ncs_equipment {
    list contained-holder {
      key "uuid";
      uses live_ncs_holder;
      description
        "References the Holder in an Equipment that is available to take other Equipments.
         For example:
         - Slot in a sub-rack
         - Slot in a Field Replaceable Unit that can take a small form-factor pluggable.";
    }
    leaf category {
      type live_ncs_equipment-category;
      description
        "This attribute provides the identifier for the form of equipments regarded as having particular shared characteristics.";
    }
    leaf equipment-location {
      type string;
      description
        "none";
    }
    leaf geographical-location {
      type string;
      description
        "none";
    }
    leaf is-expected-actual-mismatch {
      type boolean;
      description
        "none";
    }
    list expected-equipment {
      uses live_ncs_expected-equipment;
      description
        "none";
    }
    container actual-equipment {
      uses live_ncs_actual-equipment;
      description
        "none";
    }
    uses tapi-common:live_ncs_global-class;
    description
      "Represents any relevant physical thing.
       Can be either field replaceable or not field replaceable.
       Note: The model is currently constrained to inside plant.";
  }

  grouping live_ncs_holder {
    container occupying-fru {
      uses live_ncs_equipment-ref;
      description
        "The FRU that is occupying the holder.
         A holder may be unoccupied.
         An FRU may occupy more hat one holder (using or blocking are intentionally not distinguished here).";
    }
    container expected-holder {
      uses live_ncs_expected-holder;
      description
        "none";
    }
    container actual-holder {
      uses live_ncs_actual-holder;
      description
        "none";
    }
    uses tapi-common:live_ncs_global-class;
    description
      "Represents a space in an equipment in which another equipment can be fitted in the field.";
  }

  grouping live_ncs_access-port {
    list connector-pin {
      key "connector-identification pin-identification equipment-uuid";
      // NCS drop min-elements statement
      uses live_ncs_connector-pin-address;
      description
        "The list of Pins that support the AccessPort.";
    }
    uses tapi-common:live_ncs_global-class;
    description
      "A group of pins that together support a signal group where any one pin removed from the group will prevent all signals of the signal group from flowing successfully.
       In some cases the AccessPort may simply reference a single connector (e.g., where the pin-connector association is simpe such that the AccessPort references all pinsof one connector).";
  }

  grouping live_ncs_physical-span {
    list access-port {
      uses live_ncs_access-port-ref;
      key "device-uuid access-port-uuid";
      // NCS drop min-elements statement
      // NCS drop max-elements statement
      description
        "none";
    }
    list abstract-strand {
      key "local-id";
      uses live_ncs_abstract-strand;
      description
        "Both the serial segments that form an end-end strand and the parallel end-end strands.";
    }
    uses tapi-common:live_ncs_global-class;
    description
      "An adjacency between AccessPorts.
       The adjacency is supported by a group of strands between pins of the AccessPorts.
       This is a physical abstraction.";
  }

  grouping live_ncs_abstract-strand {
    list adjacent-strand {
      uses live_ncs_abstract-strand-ref;
      key "physical-span-uuid abstract-strand-local-id";
      description
        "none";
    }
    list spliced-strand {
      uses live_ncs_abstract-strand-ref;
      key "physical-span-uuid abstract-strand-local-id";
      // NCS drop max-elements statement
      description
        "none";
    }
    list connector-pin {
      key "connector-identification pin-identification equipment-uuid";
      // NCS drop max-elements statement
      uses live_ncs_connector-pin-address;
      description
        "A strand can end on two or more Pins (usually 2 pins, but a strand my be spliced to split a signal). This model supports only 2 ended strands.
         A abstract strand may be spliced at both ends and hence have no direct relationship to pins or may be connected to pins at one or both ends.
         In the essential model these Pins would be on connectors that plug in to connectors on Equipments.
         The AbstractStrand is extended to the pins of the AccessPort which are the Pins on the Connectors of the Equipment.
         In some cases it may not be relevant to represent the pin detail and hence the reference is to a connector alone.";
    }
    list strand-media-characteristics {
      key "value-name";
      uses tapi-common:live_ncs_name-and-value;
      description
        "Relevant physical properties of the abstract strand.";
    }
    uses tapi-common:live_ncs_local-class;
    description
      "This object represents an abstraction of one or more strands in series that provides sufficient detail to enable appropriate engineering.
       A strand represents a continuous long, thin piece of a medium such as glass fiber or copper wire.
       In this model a Strand:
       - a strand has two ends
       - a splice can only be between 2 strands.
       - the end of a strand may have a splice, a connector or be hidden
       - only one end can be hidden in an equipment
       - where a cable has more than two end each strand only goes between two of the ends
       This model does NOT account for multiple copper strands being spliced.";
  }

  grouping live_ncs_device {
    list equipment {
      key "uuid";
      uses live_ncs_equipment;
      description
        "none";
    }
    list access-port {
      key "uuid";
      uses live_ncs_access-port;
      description
        "none";
    }
    uses tapi-common:live_ncs_global-class;
    description
      "A logical grouping of Equipments and AccessPorts that are closely located and form a support a coherent system of related functions.";
  }

  grouping live_ncs_physical-context {
    list device {
      key "uuid";
      uses live_ncs_device;
      description
        "none";
    }
    list physical-span {
      key "uuid";
      uses live_ncs_physical-span;
      description
        "none";
    }
    uses tapi-common:live_ncs_global-class;
    description
      "none";
  }

  grouping live_ncs_supporting-physical-span {
    container physical-span {
      uses live_ncs_physical-span-ref;
      description
        "none";
    }
    description
      "none";
  }

  grouping live_ncs_supporting-access-port {
    container access-port {
      uses live_ncs_access-port-ref;
      description
        "none";
    }
    description
      "none";
  }

  grouping device-ref {
    leaf device-uuid {
      type leafref {
        path "/ncs:devices/ncs:device/ncs:live-status/tapi-common:context/tapi-equipment:physical-context/tapi-equipment:device/tapi-equipment:uuid" {
          tailf:xpath-root 2;
        }
      }
      description
        "none";
    }
    description
      "none";
  }

  grouping equipment-ref {
    uses device-ref;
    leaf equipment-uuid {
      type leafref {
        path "/ncs:devices/ncs:device/ncs:live-status/tapi-common:context/tapi-equipment:physical-context/tapi-equipment:device/tapi-equipment:equipment/tapi-equipment:uuid" {
          tailf:xpath-root 2;
        }
      }
      description
        "none";
    }
    description
      "none";
  }

  grouping equipment-holder-ref {
    uses equipment-ref;
    leaf equipment-holder-uuid {
      type leafref {
        path "/ncs:devices/ncs:device/ncs:live-status/tapi-common:context/tapi-equipment:physical-context/tapi-equipment:device/tapi-equipment:equipment/tapi-equipment:contained-holder/tapi-equipment:uuid" {
          tailf:xpath-root 2;
        }
      }
      description
        "none";
    }
    description
      "none";
  }

  grouping access-port-ref {
    uses device-ref;
    leaf access-port-uuid {
      type leafref {
        path "/ncs:devices/ncs:device/ncs:live-status/tapi-common:context/tapi-equipment:physical-context/tapi-equipment:device/tapi-equipment:access-port/tapi-equipment:uuid" {
          tailf:xpath-root 2;
        }
      }
      description
        "none";
    }
    description
      "none";
  }

  grouping physical-span-ref {
    leaf physical-span-uuid {
      type leafref {
        path "/ncs:devices/ncs:device/ncs:live-status/tapi-common:context/tapi-equipment:physical-context/tapi-equipment:physical-span/tapi-equipment:uuid" {
          tailf:xpath-root 2;
        }
      }
      description
        "none";
    }
    description
      "none";
  }

  grouping abstract-strand-ref {
    uses physical-span-ref;
    leaf abstract-strand-local-id {
      type leafref {
        path "/ncs:devices/ncs:device/ncs:live-status/tapi-common:context/tapi-equipment:physical-context/tapi-equipment:physical-span/tapi-equipment:abstract-strand/tapi-equipment:local-id" {
          tailf:xpath-root 2;
        }
      }
      description
        "none";
    }
    description
      "none";
  }

  grouping connector-pin-address {
    leaf connector-identification {
      type string;
      description
        "Identification of the Connector in the context of the referenced Equipment.";
    }
    leaf pin-identification {
      type string;
      description
        "Where relevant, identification of the Pin in the context of the connector.
         Where the whole connector is used, then individual Pins need not be identified.
         Simple alternative to pinAndRole.";
    }
    leaf equipment-uuid {
      type tapi-common:uuid;
      description
        "Reference to the Equipment that is fitted with the Connector/Pin.";
    }
    // NCS drop config false list 'pin-and-role'
    description
      "The identification of the location of the Connector and/or Pin.";
  }

  grouping actual-equipment {
    // NCS drop config false list 'actual-non-field-replaceable-module'
    // NCS drop config false container 'common-actual-properties'
    // NCS drop config false container 'common-equipment-properties'
    description
      "The equipment that is actually present in the physical network.
       It will expose all dynamic properties and some critical static properties.";
  }

  grouping actual-holder {
    // NCS drop config false container 'common-holder-properties'
    description
      "A holder in the ActualEquipment.";
  }

  grouping actual-non-field-replaceable-module {
    // NCS drop config false container 'common-actual-properties'
    // NCS drop config false container 'common-equipment-properties'
    description
      "A structure that represents an actual equipment that cannot be replaced in the field.
       Is simply a subordinate part of an ActualEquipment (FRU).
       Does not have any exposed holders (any associated holders are assumed to belong to the containing FRU).
       Does not have any connectors (any associated connectors are assumed to belong to the containing FRU).
      ";
  }

  grouping common-actual-properties {
    leaf asset-instance-identifier {
      type string;
      description
        "This attribute represents the asset identifier of this instance from the manufacturer's perspective.";
    }
    leaf is-powered {
      type boolean;
      description
        "The state of the power being supplied to the equipment.
         Note that this attribute summarizes the power state.
         Full details on the actual power system would be provided from a number of PC instances representing the relevant parts of the Power function (e.g. different voltage supplies).";
    }
    leaf manufacture-date {
      type tapi-common:date-and-time;
      description
        "This attribute represents the date on which this instance is manufactured.";
    }
    leaf serial-number {
      type string;
      description
        "This attribute represents the serial number of this instance.";
    }
    leaf temperature {
      type decimal64 {
        fraction-digits 7;
      }
      description
        "The measured temperature of the Equipment.";
    }
    description
      "Properties common to actual Equipment.";
  }

  grouping common-equipment-properties {
    leaf asset-type-identifier {
      type string;
      description
        "Represents the invariant properties of the equipment asset allocated by the operator that define and characterize the type.";
    }
    leaf equipment-type-description {
      type string;
      description
        "Text describing the type of Equipment.";
    }
    leaf equipment-type-identifier {
      type string;
      description
        "This attribute identifies the part type of the equipment.";
    }
    leaf equipment-type-name {
      type string;
      description
        "This attribute identifies the type of the equipment.";
    }
    leaf equipment-type-version {
      type string;
      description
        "This attribute identifies the version of the equipment.";
    }
    leaf manufacturer-identifier {
      type string;
      description
        "The formal unique identifier of the manufacturer.";
    }
    leaf manufacturer-name {
      type string;
      description
        "The formal name of the manufacturer of the Equipment.";
    }
    description
      "Properties common to all aspects of Equipment.";
  }

  grouping common-holder-properties {
    leaf holder-category {
      type holder-category;
      description
        "The type of holder.";
    }
    leaf is-guided {
      type boolean;
      description
        "This attribute indicates whether the holder has guides that constrain the position of the equipment in the holder or not.";
    }
    leaf holder-location {
      type string;
      description
        "The relative position of the holder in the context of its containing equipment along with the position of that containing Equipment (and further recursion).";
    }
    description
      "Properties common to all aspects of Holder.";
  }

  grouping expected-equipment {
    // NCS drop config false list 'expected-non-field-replaceable-module'
    // NCS drop config false list 'expected-holder'
    // NCS drop config false container 'common-equipment-properties'
    description
      "A definition of the restrictions on the equipment that is expected to be present in the physical network at a particular 'place'.
       The expected equipment will state the type and may constrain any other invariant properties.
       It may also provide desired ranges for dynamic properties.";
  }

  grouping expected-holder {
    // NCS drop config false container 'common-holder-properties'
    description
      "A definition of a holder expected in the ActualEquipment (i.e. an ActualHolder) as part of the constraints provided by the ExpectedEquipment.";
  }

  grouping expected-non-field-replaceable-module {
    // NCS drop config false container 'common-equipment-properties'
    description
      "A structure that represents an expected equipment that cannot be replaced in the field.
       Is simply a subordinate part of an ExpectedEquipment (FRU).
       Does not have any exposed holders (any associated holders are assumed to belong to the containing FRU).
       Does not have any connectors (any associated connectors are assumed to belong to the containing FRU).
      ";
  }

  grouping pin-and-role {
    // NCS drop config false leaf 'location-in-connector'
    // NCS drop config false leaf-list 'pin-role'
    // NCS drop config false leaf 'pin-name'
    description
      "Provides an opportunity, for a pin, to give the location of the pin and the role of the pin.";
  }

  grouping equipment {
    // NCS drop config false list 'contained-holder'
    // NCS drop config false leaf category
    // NCS drop config false leaf 'equipment-location'
    // NCS drop config false leaf 'geographical-location'
    // NCS drop config false leaf 'is-expected-actual-mismatch'
    list expected-equipment {
      uses expected-equipment;
      description
        "none";
    }
    container actual-equipment {
      uses actual-equipment;
      description
        "none";
    }
    uses tapi-common:global-class;
    description
      "Represents any relevant physical thing.
       Can be either field replaceable or not field replaceable.
       Note: The model is currently constrained to inside plant.";
  }

  grouping holder {
    // NCS drop config false container 'occupying-fru'
    // NCS drop config false container 'expected-holder'
    // NCS drop config false container 'actual-holder'
    uses tapi-common:global-class;
    description
      "Represents a space in an equipment in which another equipment can be fitted in the field.";
  }

  grouping access-port {
    // NCS drop config false list 'connector-pin'
    uses tapi-common:global-class;
    description
      "A group of pins that together support a signal group where any one pin removed from the group will prevent all signals of the signal group from flowing successfully.
       In some cases the AccessPort may simply reference a single connector (e.g., where the pin-connector association is simpe such that the AccessPort references all pinsof one connector).";
  }

  grouping physical-span {
    // NCS drop config false list 'access-port'
    // NCS drop config false list 'abstract-strand'
    uses tapi-common:global-class;
    description
      "An adjacency between AccessPorts.
       The adjacency is supported by a group of strands between pins of the AccessPorts.
       This is a physical abstraction.";
  }

  grouping abstract-strand {
    // NCS drop config false list 'adjacent-strand'
    // NCS drop config false list 'spliced-strand'
    // NCS drop config false list 'connector-pin'
    // NCS drop config false list 'strand-media-characteristics'
    uses tapi-common:local-class;
    description
      "This object represents an abstraction of one or more strands in series that provides sufficient detail to enable appropriate engineering.
       A strand represents a continuous long, thin piece of a medium such as glass fiber or copper wire.
       In this model a Strand:
       - a strand has two ends
       - a splice can only be between 2 strands.
       - the end of a strand may have a splice, a connector or be hidden
       - only one end can be hidden in an equipment
       - where a cable has more than two end each strand only goes between two of the ends
       This model does NOT account for multiple copper strands being spliced.";
  }

  grouping device {
    // NCS drop config false list equipment
    // NCS drop config false list 'access-port'
    uses tapi-common:global-class;
    description
      "A logical grouping of Equipments and AccessPorts that are closely located and form a support a coherent system of related functions.";
  }

  grouping physical-context {
    // NCS drop config false list device
    // NCS drop config false list 'physical-span'
    uses tapi-common:global-class;
    description
      "none";
  }

  grouping supporting-physical-span {
    container physical-span {
      uses physical-span-ref;
      description
        "none";
    }
    description
      "none";
  }

  grouping supporting-access-port {
    container access-port {
      uses access-port-ref;
      description
        "none";
    }
    description
      "none";
  }

  augment "/ncs:devices/ncs:device/ncs:rpc" {
    container rpc-get-physical-span {
      tailf:ncs-device-type "netconf";
      tailf:display-when "not(../../ncs:module) or ../../ncs:module[ncs:name='tapi-equipment']";
      tailf:action get-physical-span {
        tailf:actionpoint ncsproxy {
          tailf:internal;
        }
        description
          "none";
        input {
          leaf uuid {
            type tapi-common:ncs_rpc_notif_uuid;
            description
              "UUID: An identifier that is universally unique within an identifier space, where the identifier space is itself globally unique, and immutable.
               An UUID carries no semantics with respect to the purpose or state of the entity.
               UUID here uses string representation as defined in RFC 4122.  The canonical representation uses lowercase characters.
               Pattern: [0-9a-fA-F]{8}-[0-9a-fA-F]{4}-[0-9a-fA-F]{4}-' + '[0-9a-fA-F]{4}-[0-9a-fA-F]{12}
               Example of a UUID in string representation: f81d4fae-7dec-11d0-a765-00a0c91e6bf6";
          }
        }
        output {
          container physical-span {
            uses ncs_rpc_notif_physical-span;
            description
              "none";
          }
        }
      }
    }
  }
  augment "/ncs:devices/ncs:device-group/ncs:ned-id/ncs:rpc" {
    container rpc-get-physical-span {
      tailf:ncs-device-type "netconf";
      tailf:display-when "../../ncs:id = 'onf-tapi-nc-2.0:onf-tapi-nc-2.0'";
      tailf:action get-physical-span {
        tailf:actionpoint ncsproxy {
          tailf:internal;
        }
        description
          "none";
        input {
          leaf uuid {
            type tapi-common:ncs_rpc_notif_uuid;
            description
              "UUID: An identifier that is universally unique within an identifier space, where the identifier space is itself globally unique, and immutable.
               An UUID carries no semantics with respect to the purpose or state of the entity.
               UUID here uses string representation as defined in RFC 4122.  The canonical representation uses lowercase characters.
               Pattern: [0-9a-fA-F]{8}-[0-9a-fA-F]{4}-[0-9a-fA-F]{4}-' + '[0-9a-fA-F]{4}-[0-9a-fA-F]{12}
               Example of a UUID in string representation: f81d4fae-7dec-11d0-a765-00a0c91e6bf6";
          }
        }
        output {
          container "device" {
            leaf "name" {
              type string;
            }
            leaf "info" {
              type string;
            }
            container "result" {
              container physical-span {
                uses ncs_rpc_notif_physical-span;
                description
                  "none";
              }
            }
          }
        }
      }
    }
  }
  augment "/ncs:devices/ncs:device/ncs:rpc" {
    container rpc-get-device {
      tailf:ncs-device-type "netconf";
      tailf:display-when "not(../../ncs:module) or ../../ncs:module[ncs:name='tapi-equipment']";
      tailf:action get-device {
        tailf:actionpoint ncsproxy {
          tailf:internal;
        }
        description
          "none";
        input {
          leaf uuid {
            type tapi-common:ncs_rpc_notif_uuid;
            description
              "UUID: An identifier that is universally unique within an identifier space, where the identifier space is itself globally unique, and immutable.
               An UUID carries no semantics with respect to the purpose or state of the entity.
               UUID here uses string representation as defined in RFC 4122.  The canonical representation uses lowercase characters.
               Pattern: [0-9a-fA-F]{8}-[0-9a-fA-F]{4}-[0-9a-fA-F]{4}-' + '[0-9a-fA-F]{4}-[0-9a-fA-F]{12}
               Example of a UUID in string representation: f81d4fae-7dec-11d0-a765-00a0c91e6bf6";
          }
        }
        output {
          container device {
            uses ncs_rpc_notif_device;
            description
              "none";
          }
        }
      }
    }
  }
  augment "/ncs:devices/ncs:device-group/ncs:ned-id/ncs:rpc" {
    container rpc-get-device {
      tailf:ncs-device-type "netconf";
      tailf:display-when "../../ncs:id = 'onf-tapi-nc-2.0:onf-tapi-nc-2.0'";
      tailf:action get-device {
        tailf:actionpoint ncsproxy {
          tailf:internal;
        }
        description
          "none";
        input {
          leaf uuid {
            type tapi-common:ncs_rpc_notif_uuid;
            description
              "UUID: An identifier that is universally unique within an identifier space, where the identifier space is itself globally unique, and immutable.
               An UUID carries no semantics with respect to the purpose or state of the entity.
               UUID here uses string representation as defined in RFC 4122.  The canonical representation uses lowercase characters.
               Pattern: [0-9a-fA-F]{8}-[0-9a-fA-F]{4}-[0-9a-fA-F]{4}-' + '[0-9a-fA-F]{4}-[0-9a-fA-F]{12}
               Example of a UUID in string representation: f81d4fae-7dec-11d0-a765-00a0c91e6bf6";
          }
        }
        output {
          container "device" {
            leaf "name" {
              type string;
            }
            leaf "info" {
              type string;
            }
            container "result" {
              container device {
                uses ncs_rpc_notif_device;
                description
                  "none";
              }
            }
          }
        }
      }
    }
  }
  augment "/ncs:devices/ncs:device/ncs:rpc" {
    container rpc-get-physical-span-list {
      tailf:ncs-device-type "netconf";
      tailf:display-when "not(../../ncs:module) or ../../ncs:module[ncs:name='tapi-equipment']";
      tailf:action get-physical-span-list {
        tailf:actionpoint ncsproxy {
          tailf:internal;
        }
        description
          "none";
        output {
          list physical-span {
            key "uuid";
            uses ncs_rpc_notif_physical-span;
            description
              "none";
          }
        }
      }
    }
  }
  augment "/ncs:devices/ncs:device-group/ncs:ned-id/ncs:rpc" {
    container rpc-get-physical-span-list {
      tailf:ncs-device-type "netconf";
      tailf:display-when "../../ncs:id = 'onf-tapi-nc-2.0:onf-tapi-nc-2.0'";
      tailf:action get-physical-span-list {
        tailf:actionpoint ncsproxy {
          tailf:internal;
        }
        description
          "none";
        output {
          container "device" {
            leaf "name" {
              type string;
            }
            leaf "info" {
              type string;
            }
            container "result" {
              list physical-span {
                key "uuid";
                uses ncs_rpc_notif_physical-span;
                description
                  "none";
              }
            }
          }
        }
      }
    }
  }
  augment "/ncs:devices/ncs:device/ncs:rpc" {
    container rpc-get-device-list {
      tailf:ncs-device-type "netconf";
      tailf:display-when "not(../../ncs:module) or ../../ncs:module[ncs:name='tapi-equipment']";
      tailf:action get-device-list {
        tailf:actionpoint ncsproxy {
          tailf:internal;
        }
        description
          "none";
        output {
          list device {
            key "uuid";
            uses ncs_rpc_notif_device;
            description
              "none";
          }
        }
      }
    }
  }
  augment "/ncs:devices/ncs:device-group/ncs:ned-id/ncs:rpc" {
    container rpc-get-device-list {
      tailf:ncs-device-type "netconf";
      tailf:display-when "../../ncs:id = 'onf-tapi-nc-2.0:onf-tapi-nc-2.0'";
      tailf:action get-device-list {
        tailf:actionpoint ncsproxy {
          tailf:internal;
        }
        description
          "none";
        output {
          container "device" {
            leaf "name" {
              type string;
            }
            leaf "info" {
              type string;
            }
            container "result" {
              list device {
                key "uuid";
                uses ncs_rpc_notif_device;
                description
                  "none";
              }
            }
          }
        }
      }
    }
  }
  augment "/ncs:devices/ncs:template/ncs:ned-id/ncs:config/tapi-common:context" {
    container physical-context {
      uses ncs_template_physical-context;
      description
        "none";
    }
    description
      "none";
  }
  augment "/ncs:devices/ncs:device/ncs:live-status/tapi-common:context" {
    container physical-context {
      tailf:ncs-device-type "netconf";
      tailf:display-when "not(../../../ncs:module) or ../../../ncs:module[ncs:name='tapi-equipment'] or (../../../ncs:live-status-protocol[not(ncs:capability)]) or (../../../ncs:live-status-protocol/ncs:capability/ncs:module[.='tapi-equipment'])";
      uses live_ncs_physical-context;
      description
        "none";
    }
    description
      "none";
  }
  augment "/ncs:devices/ncs:device/ncs:config/tapi-common:context" {
    container physical-context {
      tailf:ncs-device-type "netconf";
      tailf:display-when "not(../../../ncs:module) or ../../../ncs:module[ncs:name='tapi-equipment']";
      uses physical-context;
      description
        "none";
    }
    description
      "none";
  }
  augment "/ncs:devices/ncs:device/ncs:live-status/tapi-common:context/tapi-topology:topology-context/tapi-topology:topology/tapi-topology:node" {
    container supporting-physical-span {
      tailf:ncs-device-type "netconf";
      tailf:display-when "not(../../../../../../ncs:module) or ../../../../../../ncs:module[ncs:name='tapi-equipment'] or (../../../../../../ncs:live-status-protocol[not(ncs:capability)]) or (../../../../../../ncs:live-status-protocol/ncs:capability/ncs:module[.='tapi-equipment'])";
      uses live_ncs_supporting-physical-span;
      description
        "none";
    }
    description
      "none";
  }
  augment "/ncs:devices/ncs:device/ncs:live-status/tapi-common:context/tapi-topology:topology-context/tapi-topology:topology/tapi-topology:node/tapi-topology:owned-node-edge-point" {
    container supporting-access-port {
      tailf:ncs-device-type "netconf";
      tailf:display-when "not(../../../../../../../ncs:module) or ../../../../../../../ncs:module[ncs:name='tapi-equipment'] or (../../../../../../../ncs:live-status-protocol[not(ncs:capability)]) or (../../../../../../../ncs:live-status-protocol/ncs:capability/ncs:module[.='tapi-equipment'])";
      uses live_ncs_supporting-access-port;
      description
        "none";
    }
    description
      "none";
  }

  identity EQUIPMENT_OBJECT_TYPE_ABSTRACT_STRAND {
    base EQUIPMENT_OBJECT_TYPE;
    description
      "none";
  }

  identity EQUIPMENT_OBJECT_TYPE_PHYSICAL_SPAN {
    base EQUIPMENT_OBJECT_TYPE;
    description
      "none";
  }

  identity EQUIPMENT_OBJECT_TYPE_HOLDER {
    base EQUIPMENT_OBJECT_TYPE;
    description
      "none";
  }

  identity EQUIPMENT_OBJECT_TYPE_EQUIPMENT {
    base EQUIPMENT_OBJECT_TYPE;
    description
      "none";
  }

  identity EQUIPMENT_OBJECT_TYPE_ACCESS_PORT {
    base EQUIPMENT_OBJECT_TYPE;
    description
      "none";
  }

  identity EQUIPMENT_OBJECT_TYPE_DEVICE {
    base EQUIPMENT_OBJECT_TYPE;
    description
      "none";
  }

  identity EQUIPMENT_OBJECT_TYPE {
    description
      "none";
  }

  identity HOLDER_CATEGORY_SLOT {
    base HOLDER_CATEGORY;
    description
      "A guided holder with fixed connectors.
       The guided holder is designed to take a particular form of CIRCUIT_PACK or SMALL_FORMFACTOR_PLUGGABLE";
  }

  identity HOLDER_CATEGORY {
    description
      "none";
  }

  identity EQUIPMENT_CATEGORY_RACK {
    base EQUIPMENT_CATEGORY;
    description
      "A mechanical assembly with cabling and predefined mounting points for particular SUBRACK types.
       The assembly is designed to be mounted on the floor in a row with other RACKs.";
  }

  identity EQUIPMENT_CATEGORY_STAND_ALONE_UNIT {
    base EQUIPMENT_CATEGORY;
    description
      "An assembly with connectors for cabling and potentially with holders.
       The assembly is designed to be mounted in a freeform environment (on a table or simple mechanical cabinet).
       May support holders (SLOTs) for CIRCUIT_PACKs or for SMALL_FORMFACTOR_PLUGGABLEs.";
  }

  identity EQUIPMENT_CATEGORY_SMALL_FORMFACTOR_PLUGGABLE {
    base EQUIPMENT_CATEGORY;
    description
      "A small assembly (compared to a CIRCUIT_PACK) with connectors compatible with those in a holder.
       The assembly is designed to be mounted in a holder (SLOT) of a CIRCUIT_PACK or STAND_ALONE_UNIT.";
  }

  identity EQUIPMENT_CATEGORY_CIRCUIT_PACK {
    base EQUIPMENT_CATEGORY;
    description
      "An assembly with connectors compatible with those in a holder.
       The assembly is designed to be mounted in a holder (SLOT) of a SUBRACK.
       May also support holders (SLOTs) for SMALL_FORMFACTOR_PLUGGABLEs.";
  }

  identity EQUIPMENT_CATEGORY_SUBRACK {
    base EQUIPMENT_CATEGORY;
    description
      "An assembly with holders designed to accommodate CIRCUIT_PACKs.
       The assembly is designed to be mounted in a RACK.";
  }

  identity EQUIPMENT_CATEGORY {
    description
      "none";
  }

  identity CONNECTOR_AND_PIN_ORIENTATION_SYMMETRIC_NEUTRAL {
    base CONNECTOR_AND_PIN_ORIENTATION;
    description
      "The pin (and housing) orientation combination is such that it is symmetric so a connector is compatible with itself.
       The connecting element may be a surface rather than protrusions or indentations.";
  }

  identity CONNECTOR_AND_PIN_ORIENTATION_FEMALE {
    base CONNECTOR_AND_PIN_ORIENTATION;
    description
      "The connecting elements are dominantly indentations.";
  }

  identity CONNECTOR_AND_PIN_ORIENTATION_MALE {
    base CONNECTOR_AND_PIN_ORIENTATION;
    description
      "The connecting elements are dominantly protrusions.";
  }

  identity CONNECTOR_AND_PIN_ORIENTATION {
    description
      "none";
  }
}
