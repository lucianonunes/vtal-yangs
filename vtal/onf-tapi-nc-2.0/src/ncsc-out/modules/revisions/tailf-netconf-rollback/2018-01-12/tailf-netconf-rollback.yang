module tailf-netconf-rollback {
  // Generated by yanger -t ncs
  tailf:mount-id "onf-tapi-nc-2.0:onf-tapi-nc-2.0";
  tailf:ncs-device-type "netconf";

  yang-version 1.1;
  namespace "http://tail-f.com/ns/netconf/rollback";
  prefix netconf-rollback;

  import ietf-netconf {
    prefix nc;
  }
  import tailf-netconf-transactions {
    prefix tr;
  }
  import tailf-common {
    prefix tailf;
  }
  import tailf-ncs {
    prefix ncs;
  }

  organization
    "Tail-f Systems";
  description
    "Extends the NETCONF server with rollback specific meta data.

     Copyright 2018 Cisco Systems, Inc.
     All rights reserved.
     Permission is hereby granted to redistribute this file without
     modification.";

  revision 2018-01-12 {
    description
      "Initial revision.";
  }

  grouping ncs_template_rollback-meta-data {
    leaf rollback-label {
      type string;
    }
    leaf rollback-comment {
      type string;
    }
  }

  grouping ncs_rpc_notif_rollback-meta-data {
    leaf rollback-label {
      type string;
    }
    leaf rollback-comment {
      type string;
    }
  }

  grouping live_ncs_rollback-meta-data {
    leaf rollback-label {
      type string;
    }
    leaf rollback-comment {
      type string;
    }
  }

  grouping rollback-meta-data {
    leaf rollback-label {
      type string;
    }
    leaf rollback-comment {
      type string;
    }
  }

  augment "/ncs:devices/ncs:device/ncs:rpc/nc:rpc-edit-config/nc:edit-config/nc:input" {
    when 'nc:target/nc:running' {
      tailf:xpath-root 3;
    }
    uses ncs_rpc_notif_rollback-meta-data;
  }
  augment "/ncs:devices/ncs:device/ncs:rpc/nc:rpc-commit/nc:commit/nc:input" {
    // NCS drop if-feature statement
    uses ncs_rpc_notif_rollback-meta-data;
  }
  augment "/ncs:devices/ncs:device/ncs:rpc/tr:rpc-prepare-transaction/tr:prepare-transaction/tr:input" {
    uses ncs_rpc_notif_rollback-meta-data;
  }
}
