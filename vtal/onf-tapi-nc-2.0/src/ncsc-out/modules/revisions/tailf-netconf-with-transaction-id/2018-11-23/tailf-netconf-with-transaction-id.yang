module tailf-netconf-with-transaction-id {
  // Generated by yanger -t ncs
  tailf:mount-id "onf-tapi-nc-2.0:onf-tapi-nc-2.0";
  tailf:ncs-device-type "netconf";

  yang-version 1.1;
  namespace "http://tail-f.com/ns/netconf/with-transaction-id";
  prefix wtxid;

  import ietf-netconf {
    prefix nc;
  }
  import tailf-netconf-transactions {
    prefix tr;
  }
  import tailf-common {
    prefix tailf;
  }
  import tailf-ncs {
    prefix ncs;
  }

  description
    "This module adds a parameter 'with-transaction-id' to the
     following rpcs:

       o  edit-config
       o  copy-config
       o  commit
       o  commit-transaction

     This parameter lets the client request that the datastore's
     transaction id is returned in the reply to the request.

     This can be used to avoid a round-trip, which is otherwise needed
     to get the transaction id from

       /netconf-state/datastores/datastore/transaction-id

     The transaction id is only availabe for the running configuration
     datastore.

     Copyright 2018 Cisco Systems, Inc.
     All rights reserved.
     Permission is hereby granted to redistribute this file without
     modification.";

  revision 2018-11-23 {
    description
      "Initial revision.";
  }

  grouping ncs_template_with-transaction-id-params {
    leaf with-transaction-id {
      type empty;
    }
  }

  grouping ncs_template_with-transaction-id-reply {
    leaf transaction-id {
      type string;
    }
  }

  grouping ncs_rpc_notif_with-transaction-id-params {
    leaf with-transaction-id {
      type empty;
    }
  }

  grouping ncs_rpc_notif_with-transaction-id-reply {
    leaf transaction-id {
      type string;
    }
  }

  grouping live_ncs_with-transaction-id-params {
    leaf with-transaction-id {
      type empty;
    }
  }

  grouping live_ncs_with-transaction-id-reply {
    leaf transaction-id {
      type string;
    }
  }

  grouping with-transaction-id-params {
    leaf with-transaction-id {
      type empty;
    }
  }

  grouping with-transaction-id-reply {
    leaf transaction-id {
      type string;
    }
  }

  augment "/ncs:devices/ncs:device/ncs:rpc/nc:rpc-edit-config/nc:edit-config/nc:input" {
    uses ncs_rpc_notif_with-transaction-id-params;
  }
  augment "/ncs:devices/ncs:device/ncs:rpc/nc:rpc-edit-config/nc:edit-config/nc:output" {
    uses ncs_rpc_notif_with-transaction-id-reply;
  }
  augment "/ncs:devices/ncs:device/ncs:rpc/nc:rpc-copy-config/nc:copy-config/nc:input" {
    uses ncs_rpc_notif_with-transaction-id-params;
  }
  augment "/ncs:devices/ncs:device/ncs:rpc/nc:rpc-copy-config/nc:copy-config/nc:output" {
    uses ncs_rpc_notif_with-transaction-id-reply;
  }
  augment "/ncs:devices/ncs:device/ncs:rpc/nc:rpc-commit/nc:commit/nc:input" {
    uses ncs_rpc_notif_with-transaction-id-params;
  }
  augment "/ncs:devices/ncs:device/ncs:rpc/nc:rpc-commit/nc:commit/nc:output" {
    uses ncs_rpc_notif_with-transaction-id-reply;
  }
  augment "/ncs:devices/ncs:device/ncs:rpc/tr:rpc-commit-transaction/tr:commit-transaction/tr:input" {
    uses ncs_rpc_notif_with-transaction-id-params;
  }
  augment "/ncs:devices/ncs:device/ncs:rpc/tr:rpc-commit-transaction/tr:commit-transaction/tr:output" {
    uses ncs_rpc_notif_with-transaction-id-reply;
  }
}
