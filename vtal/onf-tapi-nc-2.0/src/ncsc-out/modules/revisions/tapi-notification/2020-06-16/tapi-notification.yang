module tapi-notification {
  // Generated by yanger -t ncs
  tailf:mount-id "onf-tapi-nc-2.0:onf-tapi-nc-2.0";
  tailf:ncs-device-type "netconf";

  namespace "urn:onf:otcc:yang:tapi-notification";
  prefix tapi-notification;

  import tapi-common {
    prefix tapi-common;
  }
  import tailf-common {
    prefix tailf;
  }
  import tailf-ncs {
    prefix ncs;
  }

  organization
    "ONF OTCC (Open Transport Configuration & Control) Project";
  contact
    "
     Project Web: <https://urldefense.com/v3/__https://wiki.opennetworking.org/display/OTCC/TAPI__;!!OSsGDw!d_dJlNtYLmD585It0DKukzB2TS5KZqBZQ-pdI1D-6c6c5hRDotd6G39KDEbL$ >
     Project List: <mailto:transport-api@opennetworking.org>
     Editor: Karthik Sethuraman <mailto:karthik.sethuraman@necam.com>
     Andrea Mazzini <mailto:andrea.mazzini@nokia.com>
     Arturo Mayoral <mailto:arturo.mayoral@telefonica.com>
     Nigel Davis <mailto:ndavis@ciena.com>";
  description
    "
     This module contains TAPI Notification Model definitions.
     Source: TapiNotification.uml
     - The TAPI YANG models included in this TAPI release are a *normative* part of the TAPI SDK.
     - The YANG specifications have been generated from the corresponding UML model using the [ONF EAGLE UML2YANG mapping tool]
     <https://urldefense.com/v3/__https://github.com/OpenNetworkingFoundation/EagleUmlYang__;!!OSsGDw!d_dJlNtYLmD585It0DKukzB2TS5KZqBZQ-pdI1D-6c6c5hRDotd6G4QHf0bG$ >
     and further edited manually to comply with the [ONF IISOMI UML2YANG mapping guidelines]
     <https://urldefense.com/v3/__https://wiki.opennetworking.org/display/OIMT/UML*-*YANG*Guidelines__;Kysr!!OSsGDw!d_dJlNtYLmD585It0DKukzB2TS5KZqBZQ-pdI1D-6c6c5hRDotd6G8IIivez$ >
     - Status of YANG model artifacts can be determined by referring to the corresponding UML artifacts.
     As described in the UML models, some artifacts are considered *experimental*, and thus the corresponding YANG artifacts.
     - The ONF TAPI release process does not guarantee backward compatibility of YANG models across major versions of TAPI releases.
     The YANG model backward compatibility criteria are outlined in section 11 of <https://urldefense.com/v3/__https://tools.ietf.org/html/rfc7950__;!!OSsGDw!d_dJlNtYLmD585It0DKukzB2TS5KZqBZQ-pdI1D-6c6c5hRDotd6G3bKxRf2$ >.
     YANG models included in this release may not be backward compatible with previous TAPI releases.
     Copyright (c) 2018 Open Networking Foundation (ONF). All rights reserved.
     License: This module is distributed under the Apache License 2.0";

  revision 2020-06-16 {
    description
      "ONF Transport API version 2.1.3.
       - Added DEVICE to ObjectType.
       Changes included in this TAPI release (v2.1.3) are listed in
       <https://urldefense.com/v3/__https://github.com/OpenNetworkingFoundation/TAPI/blob/develop_v2_1/CHANGE_LOG/change-log.2.1.3.md__;!!OSsGDw!d_dJlNtYLmD585It0DKukzB2TS5KZqBZQ-pdI1D-6c6c5hRDotd6G7tqhxFK$ >";
    reference
      "ONF-TR-527, ONF-TR-512, ONF-TR-531, RFC 7950, RFC 6087 and ONF TAPI UML model
       <https://urldefense.com/v3/__https://github.com/OpenNetworkingFoundation/TAPI/tree/v2.1.0/UML__;!!OSsGDw!d_dJlNtYLmD585It0DKukzB2TS5KZqBZQ-pdI1D-6c6c5hRDotd6G7KeAhLL$ >";
  }
  revision 2019-07-16 {
    description
      "ONF Transport API version 2.1.2.
       Changes included in this TAPI release (v2.1.2) are listed in
       <https://urldefense.com/v3/__https://github.com/OpenNetworkingFoundation/TAPI/blob/develop_v2_1/CHANGE_LOG/change-log.2.1.2.md__;!!OSsGDw!d_dJlNtYLmD585It0DKukzB2TS5KZqBZQ-pdI1D-6c6c5hRDotd6G7eDS6-t$ >";
    reference
      "ONF-TR-527, ONF-TR-512, ONF-TR-531, RFC 7950, RFC 6087 and ONF TAPI UML model
       <https://urldefense.com/v3/__https://github.com/OpenNetworkingFoundation/TAPI/tree/v2.1.0/UML__;!!OSsGDw!d_dJlNtYLmD585It0DKukzB2TS5KZqBZQ-pdI1D-6c6c5hRDotd6G7KeAhLL$ >";
  }
  revision 2018-12-10 {
    description
      "ONF Transport API version 2.1.1.
       Changes included in this TAPI release (v2.1.1) are listed in
       <https://urldefense.com/v3/__https://github.com/OpenNetworkingFoundation/TAPI/blob/develop/CHANGE_LOG/change-log.2.1.1.md__;!!OSsGDw!d_dJlNtYLmD585It0DKukzB2TS5KZqBZQ-pdI1D-6c6c5hRDotd6G1ftwU5J$ >";
    reference
      "ONF-TR-527, ONF-TR-512, ONF-TR-531, RFC 7950, RFC 6087 and ONF TAPI UML model
       <https://urldefense.com/v3/__https://github.com/OpenNetworkingFoundation/TAPI/tree/v2.1.0/UML__;!!OSsGDw!d_dJlNtYLmD585It0DKukzB2TS5KZqBZQ-pdI1D-6c6c5hRDotd6G7KeAhLL$ >";
  }
  revision 2018-10-16 {
    description
      "ONF Transport API version 2.1.0.
       Changes included in this TAPI release (v2.1.0) are listed in
       <https://urldefense.com/v3/__https://github.com/OpenNetworkingFoundation/TAPI/blob/develop/CHANGE_LOG/change-log.2.1.0.md__;!!OSsGDw!d_dJlNtYLmD585It0DKukzB2TS5KZqBZQ-pdI1D-6c6c5hRDotd6G-5JStw4$ >";
    reference
      "ONF-TR-527, ONF-TR-512, ONF-TR-531, RFC 7950, RFC 6087 and ONF TAPI UML model
       <https://urldefense.com/v3/__https://github.com/OpenNetworkingFoundation/TAPI/tree/v2.1.0/UML__;!!OSsGDw!d_dJlNtYLmD585It0DKukzB2TS5KZqBZQ-pdI1D-6c6c5hRDotd6G7KeAhLL$ >";
  }
  revision 2018-03-07 {
    description
      "ONF Transport API version 2.0.2
       This YANG module has been generated from the TAPI UML Model using the IISOMI-Eagle xmi2yang mapping tool.
       Changes in this revision: <https://urldefense.com/v3/__https://github.com/OpenNetworkingFoundation/TAPI/blob/develop/CHANGE_LOG/change-log.2.0.2.md__;!!OSsGDw!d_dJlNtYLmD585It0DKukzB2TS5KZqBZQ-pdI1D-6c6c5hRDotd6G1Yf4AAN$ >";
    reference
      "ONF-TR-527, ONF-TR-512, ONF-TR-531, RFC 6020, RFC 6087 and ONF TAPI UML model
       <https://urldefense.com/v3/__https://github.com/OpenNetworkingFoundation/TAPI/tree/v2.0.2/UML__;!!OSsGDw!d_dJlNtYLmD585It0DKukzB2TS5KZqBZQ-pdI1D-6c6c5hRDotd6G27-pJK_$ >";
  }
  revision 2018-02-16 {
    description
      "ONF Transport API version 2.0.1
       This YANG module has been generated from the TAPI UML Model using the IISOMI-Eagle xmi2yang mapping tool.
       Changes in this revision: <https://urldefense.com/v3/__https://github.com/OpenNetworkingFoundation/TAPI/blob/develop/CHANGE_LOG/change-log.2.0.1.md__;!!OSsGDw!d_dJlNtYLmD585It0DKukzB2TS5KZqBZQ-pdI1D-6c6c5hRDotd6G8RnGvXg$ >";
    reference
      "ONF-TR-527, ONF-TR-512, ONF-TR-531, RFC 6020, RFC 6087 and ONF TAPI UML model
       <https://urldefense.com/v3/__https://github.com/OpenNetworkingFoundation/TAPI/tree/v2.0.1/UML__;!!OSsGDw!d_dJlNtYLmD585It0DKukzB2TS5KZqBZQ-pdI1D-6c6c5hRDotd6Gy6YoeAv$ >";
  }
  revision 2018-01-02 {
    description
      "ONF Transport API version 2.0.0
       This YANG module has been generated from the TAPI UML Model using the IISOMI-Eagle xmi2yang mapping tool.
       Changes in this revision: <https://urldefense.com/v3/__https://github.com/OpenNetworkingFoundation/TAPI/blob/develop/CHANGE_LOG/change-log.2.0.0.md__;!!OSsGDw!d_dJlNtYLmD585It0DKukzB2TS5KZqBZQ-pdI1D-6c6c5hRDotd6GyqYDgG_$ >";
    reference
      "ONF-TR-527, ONF-TR-512, ONF-TR-531, RFC 6020, RFC 6087 and ONF TAPI UML model
       <https://urldefense.com/v3/__https://github.com/OpenNetworkingFoundation/TAPI/tree/v2.0.0/UML__;!!OSsGDw!d_dJlNtYLmD585It0DKukzB2TS5KZqBZQ-pdI1D-6c6c5hRDotd6G1V9Thk9$ >";
  }

  typedef ncs_template_notification-type {
    type string;
    description
      "List of supported Notifications types.";
  }

  typedef ncs_template_object-type {
    type string;
    description
      "The list of TAPI Global Object Class types on which Notifications can be raised.";
  }

  typedef ncs_template_source-indicator {
    type string;
    description
      "none";
  }

  typedef ncs_template_subscription-state {
    type string;
    description
      "none";
  }

  typedef ncs_template_perceived-severity-type {
    type string;
    description
      "none";
  }

  typedef ncs_template_threshold-crossing-type {
    type string;
    description
      "none";
  }

  typedef ncs_template_service-affecting {
    type string;
    description
      "none";
  }

  typedef ncs_template_perceived-tca-severity {
    type string;
    description
      "none";
  }

  typedef ncs_rpc_notif_notification-type {
    type enumeration {
      enum "OBJECT_CREATION" {
        description
          "Not a normal state. The system is unable to determine the correct value.";
      }
      enum "OBJECT_DELETION" {
        description
          "none";
      }
      enum "ATTRIBUTE_VALUE_CHANGE" {
        description
          "none";
      }
      enum "ALARM_EVENT" {
        description
          "none";
      }
      enum "THRESHOLD_CROSSING_ALERT" {
        description
          "none";
      }
    }
    description
      "List of supported Notifications types.";
  }

  typedef ncs_rpc_notif_object-type {
    type enumeration {
      enum "TOPOLOGY" {
        description
          "none";
      }
      enum "NODE" {
        description
          "none";
      }
      enum "LINK" {
        description
          "none";
      }
      enum "CONNECTION" {
        description
          "none";
      }
      enum "PATH" {
        description
          "none";
      }
      enum "CONNECTIVITY_SERVICE" {
        description
          "none";
      }
      enum "VIRTUAL_NETWORK_SERVICE" {
        description
          "none";
      }
      enum "PATH_COMPUTATION_SERVICE" {
        description
          "none";
      }
      enum "NODE_EDGE_POINT" {
        description
          "none";
      }
      enum "SERVICE_INTERFACE_POINT" {
        description
          "none";
      }
      enum "CONNECTION_END_POINT" {
        description
          "none";
      }
      enum "MAINTENANCE_ENTITY_GROUP" {
        description
          "none";
      }
      enum "MAINTENANCE_ENTITY" {
        description
          "none";
      }
      enum "MEG_END_POINT" {
        description
          "none";
      }
      enum "MEG_INTERMEDIATE_POINT" {
        description
          "none";
      }
      enum "SWITCH_CONTROL" {
        description
          "none";
      }
      enum "SWITCH" {
        description
          "none";
      }
      enum "ROUTE" {
        description
          "none";
      }
      enum "NODE_RULE_GROUP" {
        description
          "none";
      }
      enum "INTER_RULE_GROUP" {
        description
          "none";
      }
      enum "RULE" {
        description
          "none";
      }
      enum "OAM_JOB" {
        description
          "none";
      }
      enum "ACCESS_PORT" {
        description
          "none";
      }
      enum "EQUIPMENT" {
        description
          "none";
      }
      enum "HOLDER" {
        description
          "none";
      }
      enum "PHYSICAL_SPAN" {
        description
          "none";
      }
      enum "ABSTRACT_STRAND" {
        description
          "none";
      }
      enum "DEVICE" {
        description
          "none";
      }
    }
    description
      "The list of TAPI Global Object Class types on which Notifications can be raised.";
  }

  typedef ncs_rpc_notif_source-indicator {
    type enumeration {
      enum "RESOURCE_OPERATION" {
        description
          "none";
      }
      enum "MANAGEMENT_OPERATION" {
        description
          "none";
      }
      enum "UNKNOWN" {
        description
          "none";
      }
    }
    description
      "none";
  }

  typedef ncs_rpc_notif_subscription-state {
    type enumeration {
      enum "SUSPENDED" {
        description
          "none";
      }
      enum "ACTIVE" {
        description
          "none";
      }
    }
    description
      "none";
  }

  typedef ncs_rpc_notif_perceived-severity-type {
    type enumeration {
      enum "CRITICAL" {
        description
          "none";
      }
      enum "MAJOR" {
        description
          "none";
      }
      enum "MINOR" {
        description
          "none";
      }
      enum "WARNING" {
        description
          "none";
      }
      enum "CLEARED" {
        description
          "none";
      }
    }
    description
      "none";
  }

  typedef ncs_rpc_notif_threshold-crossing-type {
    type enumeration {
      enum "THRESHOLD_ABOVE" {
        description
          "none";
      }
      enum "THRESHOLD_BELOW" {
        description
          "none";
      }
      enum "CLEARED" {
        description
          "none";
      }
    }
    description
      "none";
  }

  typedef ncs_rpc_notif_service-affecting {
    type enumeration {
      enum "SERVICE_AFFECTING" {
        description
          "none";
      }
      enum "NOT_SERVICE_AFFECTING" {
        description
          "none";
      }
      enum "UNKNOWN" {
        description
          "none";
      }
    }
    description
      "none";
  }

  typedef ncs_rpc_notif_perceived-tca-severity {
    type enumeration {
      enum "WARNING" {
        description
          "none";
      }
      enum "CLEAR" {
        description
          "none";
      }
    }
    description
      "none";
  }

  typedef live_ncs_notification-type {
    type enumeration {
      enum "OBJECT_CREATION" {
        description
          "Not a normal state. The system is unable to determine the correct value.";
      }
      enum "OBJECT_DELETION" {
        description
          "none";
      }
      enum "ATTRIBUTE_VALUE_CHANGE" {
        description
          "none";
      }
      enum "ALARM_EVENT" {
        description
          "none";
      }
      enum "THRESHOLD_CROSSING_ALERT" {
        description
          "none";
      }
    }
    description
      "List of supported Notifications types.";
  }

  typedef live_ncs_object-type {
    type enumeration {
      enum "TOPOLOGY" {
        description
          "none";
      }
      enum "NODE" {
        description
          "none";
      }
      enum "LINK" {
        description
          "none";
      }
      enum "CONNECTION" {
        description
          "none";
      }
      enum "PATH" {
        description
          "none";
      }
      enum "CONNECTIVITY_SERVICE" {
        description
          "none";
      }
      enum "VIRTUAL_NETWORK_SERVICE" {
        description
          "none";
      }
      enum "PATH_COMPUTATION_SERVICE" {
        description
          "none";
      }
      enum "NODE_EDGE_POINT" {
        description
          "none";
      }
      enum "SERVICE_INTERFACE_POINT" {
        description
          "none";
      }
      enum "CONNECTION_END_POINT" {
        description
          "none";
      }
      enum "MAINTENANCE_ENTITY_GROUP" {
        description
          "none";
      }
      enum "MAINTENANCE_ENTITY" {
        description
          "none";
      }
      enum "MEG_END_POINT" {
        description
          "none";
      }
      enum "MEG_INTERMEDIATE_POINT" {
        description
          "none";
      }
      enum "SWITCH_CONTROL" {
        description
          "none";
      }
      enum "SWITCH" {
        description
          "none";
      }
      enum "ROUTE" {
        description
          "none";
      }
      enum "NODE_RULE_GROUP" {
        description
          "none";
      }
      enum "INTER_RULE_GROUP" {
        description
          "none";
      }
      enum "RULE" {
        description
          "none";
      }
      enum "OAM_JOB" {
        description
          "none";
      }
      enum "ACCESS_PORT" {
        description
          "none";
      }
      enum "EQUIPMENT" {
        description
          "none";
      }
      enum "HOLDER" {
        description
          "none";
      }
      enum "PHYSICAL_SPAN" {
        description
          "none";
      }
      enum "ABSTRACT_STRAND" {
        description
          "none";
      }
      enum "DEVICE" {
        description
          "none";
      }
    }
    description
      "The list of TAPI Global Object Class types on which Notifications can be raised.";
  }

  typedef live_ncs_source-indicator {
    type enumeration {
      enum "RESOURCE_OPERATION" {
        description
          "none";
      }
      enum "MANAGEMENT_OPERATION" {
        description
          "none";
      }
      enum "UNKNOWN" {
        description
          "none";
      }
    }
    description
      "none";
  }

  typedef live_ncs_subscription-state {
    type enumeration {
      enum "SUSPENDED" {
        description
          "none";
      }
      enum "ACTIVE" {
        description
          "none";
      }
    }
    description
      "none";
  }

  typedef live_ncs_perceived-severity-type {
    type enumeration {
      enum "CRITICAL" {
        description
          "none";
      }
      enum "MAJOR" {
        description
          "none";
      }
      enum "MINOR" {
        description
          "none";
      }
      enum "WARNING" {
        description
          "none";
      }
      enum "CLEARED" {
        description
          "none";
      }
    }
    description
      "none";
  }

  typedef live_ncs_threshold-crossing-type {
    type enumeration {
      enum "THRESHOLD_ABOVE" {
        description
          "none";
      }
      enum "THRESHOLD_BELOW" {
        description
          "none";
      }
      enum "CLEARED" {
        description
          "none";
      }
    }
    description
      "none";
  }

  typedef live_ncs_service-affecting {
    type enumeration {
      enum "SERVICE_AFFECTING" {
        description
          "none";
      }
      enum "NOT_SERVICE_AFFECTING" {
        description
          "none";
      }
      enum "UNKNOWN" {
        description
          "none";
      }
    }
    description
      "none";
  }

  typedef live_ncs_perceived-tca-severity {
    type enumeration {
      enum "WARNING" {
        description
          "none";
      }
      enum "CLEAR" {
        description
          "none";
      }
    }
    description
      "none";
  }

  typedef notification-type {
    type enumeration {
      enum "OBJECT_CREATION" {
        description
          "Not a normal state. The system is unable to determine the correct value.";
      }
      enum "OBJECT_DELETION" {
        description
          "none";
      }
      enum "ATTRIBUTE_VALUE_CHANGE" {
        description
          "none";
      }
      enum "ALARM_EVENT" {
        description
          "none";
      }
      enum "THRESHOLD_CROSSING_ALERT" {
        description
          "none";
      }
    }
    description
      "List of supported Notifications types.";
  }

  typedef object-type {
    type enumeration {
      enum "TOPOLOGY" {
        description
          "none";
      }
      enum "NODE" {
        description
          "none";
      }
      enum "LINK" {
        description
          "none";
      }
      enum "CONNECTION" {
        description
          "none";
      }
      enum "PATH" {
        description
          "none";
      }
      enum "CONNECTIVITY_SERVICE" {
        description
          "none";
      }
      enum "VIRTUAL_NETWORK_SERVICE" {
        description
          "none";
      }
      enum "PATH_COMPUTATION_SERVICE" {
        description
          "none";
      }
      enum "NODE_EDGE_POINT" {
        description
          "none";
      }
      enum "SERVICE_INTERFACE_POINT" {
        description
          "none";
      }
      enum "CONNECTION_END_POINT" {
        description
          "none";
      }
      enum "MAINTENANCE_ENTITY_GROUP" {
        description
          "none";
      }
      enum "MAINTENANCE_ENTITY" {
        description
          "none";
      }
      enum "MEG_END_POINT" {
        description
          "none";
      }
      enum "MEG_INTERMEDIATE_POINT" {
        description
          "none";
      }
      enum "SWITCH_CONTROL" {
        description
          "none";
      }
      enum "SWITCH" {
        description
          "none";
      }
      enum "ROUTE" {
        description
          "none";
      }
      enum "NODE_RULE_GROUP" {
        description
          "none";
      }
      enum "INTER_RULE_GROUP" {
        description
          "none";
      }
      enum "RULE" {
        description
          "none";
      }
      enum "OAM_JOB" {
        description
          "none";
      }
      enum "ACCESS_PORT" {
        description
          "none";
      }
      enum "EQUIPMENT" {
        description
          "none";
      }
      enum "HOLDER" {
        description
          "none";
      }
      enum "PHYSICAL_SPAN" {
        description
          "none";
      }
      enum "ABSTRACT_STRAND" {
        description
          "none";
      }
      enum "DEVICE" {
        description
          "none";
      }
    }
    description
      "The list of TAPI Global Object Class types on which Notifications can be raised.";
  }

  typedef source-indicator {
    type enumeration {
      enum "RESOURCE_OPERATION" {
        description
          "none";
      }
      enum "MANAGEMENT_OPERATION" {
        description
          "none";
      }
      enum "UNKNOWN" {
        description
          "none";
      }
    }
    description
      "none";
  }

  typedef subscription-state {
    type enumeration {
      enum "SUSPENDED" {
        description
          "none";
      }
      enum "ACTIVE" {
        description
          "none";
      }
    }
    description
      "none";
  }

  typedef perceived-severity-type {
    type enumeration {
      enum "CRITICAL" {
        description
          "none";
      }
      enum "MAJOR" {
        description
          "none";
      }
      enum "MINOR" {
        description
          "none";
      }
      enum "WARNING" {
        description
          "none";
      }
      enum "CLEARED" {
        description
          "none";
      }
    }
    description
      "none";
  }

  typedef threshold-crossing-type {
    type enumeration {
      enum "THRESHOLD_ABOVE" {
        description
          "none";
      }
      enum "THRESHOLD_BELOW" {
        description
          "none";
      }
      enum "CLEARED" {
        description
          "none";
      }
    }
    description
      "none";
  }

  typedef service-affecting {
    type enumeration {
      enum "SERVICE_AFFECTING" {
        description
          "none";
      }
      enum "NOT_SERVICE_AFFECTING" {
        description
          "none";
      }
      enum "UNKNOWN" {
        description
          "none";
      }
    }
    description
      "none";
  }

  typedef perceived-tca-severity {
    type enumeration {
      enum "WARNING" {
        description
          "none";
      }
      enum "CLEAR" {
        description
          "none";
      }
    }
    description
      "none";
  }

  grouping ncs_template_notification-subscription-service {
    // NCS drop config false list notification
    // NCS drop config false container 'notification-channel'
    container subscription-filter {
      uses ncs_template_subscription-filter;
      description
        "none";
    }
    leaf subscription-state {
      type ncs_template_subscription-state;
      description
        "none";
    }
    // NCS drop config false leaf-list 'supported-notification-types'
    // NCS drop config false leaf-list 'supported-object-types'
    uses tapi-common:ncs_template_service-spec;
    description
      "none";
  }

  grouping ncs_template_subscription-filter {
    leaf-list requested-notification-types {
      // NCS patched for predictable order
      ordered-by user;
      type ncs_template_notification-type;
      description
        "none";
    }
    leaf-list requested-object-types {
      // NCS patched for predictable order
      ordered-by user;
      type ncs_template_object-type;
      description
        "none";
    }
    leaf-list requested-layer-protocols {
      // NCS patched for predictable order
      ordered-by user;
      type tapi-common:ncs_template_layer-protocol-name;
      description
        "none";
    }
    leaf-list requested-object-identifier {
      // NCS patched for predictable order
      ordered-by user;
      type tapi-common:ncs_template_uuid;
      description
        "none";
    }
    leaf include-content {
      type string;
      description
        "Indicates whether the published Notification includes content or just the Notification Id (which enables retrieval of the notification at the later stage)";
    }
    uses tapi-common:ncs_template_local-class;
    description
      "none";
  }

  grouping ncs_template_notification {
    leaf notification-type {
      type ncs_template_notification-type;
      description
        "none";
    }
    leaf target-object-type {
      type ncs_template_object-type;
      description
        "none";
    }
    leaf target-object-identifier {
      type tapi-common:ncs_template_uuid;
      description
        "none";
    }
    list target-object-name {
      // NCS patched for predictable order
      ordered-by user;
      key "value-name";
      // NCS drop min-elements statement
      uses tapi-common:ncs_template_name-and-value;
      description
        "none";
    }
    leaf event-time-stamp {
      type tapi-common:ncs_template_date-and-time;
      description
        "none";
    }
    // NCS drop config false leaf 'sequence-number'
    leaf source-indicator {
      type ncs_template_source-indicator;
      description
        "none";
    }
    leaf layer-protocol-name {
      type tapi-common:ncs_template_layer-protocol-name;
      description
        "none";
    }
    list changed-attributes {
      // NCS patched for predictable order
      ordered-by user;
      key "value-name";
      uses ncs_template_name-and-value-change;
      description
        "none";
    }
    list additional-info {
      // NCS patched for predictable order
      ordered-by user;
      key "value-name";
      uses tapi-common:ncs_template_name-and-value;
      description
        "none";
    }
    leaf additional-text {
      type string;
      description
        "none";
    }
    container tca-info {
      uses ncs_template_tca-info;
      description
        "none";
    }
    container alarm-info {
      uses ncs_template_alarm-info;
      description
        "none";
    }
    uses tapi-common:ncs_template_resource-spec;
    description
      "none";
  }

  grouping ncs_template_notification-channel {
    // NCS drop config false leaf 'stream-address'
    // NCS drop config false leaf 'next-sequence-no'
    uses tapi-common:ncs_template_local-class;
    description
      "none";
  }

  grouping ncs_template_notification-context {
    list notif-subscription {
      // NCS patched for predictable order
      ordered-by user;
      key "uuid";
      uses ncs_template_notification-subscription-service;
      description
        "none";
    }
    // NCS drop config false list notification
    description
      "none";
  }

  grouping ncs_template_alarm-info {
    // NCS drop config false leaf 'is-transient'
    // NCS drop config false leaf 'perceived-severity'
    // NCS drop config false leaf 'probable-cause'
    leaf service-affecting {
      type ncs_template_service-affecting;
      description
        "none";
    }
    description
      "none";
  }

  grouping ncs_template_tca-info {
    // NCS drop config false leaf 'is-transient'
    leaf threshold-crossing {
      type ncs_template_threshold-crossing-type;
      description
        "none";
    }
    // NCS drop config false leaf 'threshold-parameter'
    // NCS drop config false leaf 'threshold-value'
    leaf perceived-severity {
      type ncs_template_perceived-tca-severity;
      description
        "none";
    }
    leaf measurement-interval {
      type tapi-common:ncs_template_date-and-time;
      description
        "none";
    }
    leaf suspect-interval-flag {
      type string;
      description
        "none";
    }
    description
      "none";
  }

  grouping ncs_template_name-and-value-change {
    leaf value-name {
      type string;
      description
        "The name of the value. The value need not have a name.";
    }
    leaf old-value {
      type string;
      description
        "The value";
    }
    leaf new-value {
      type string;
      description
        "The value";
    }
    description
      "A scoped name-value triple, including old value and new value";
  }

  grouping ncs_rpc_notif_notification-subscription-service {
    list notification {
      key "uuid";
      config false;
      uses ncs_rpc_notif_notification;
      description
        "none";
    }
    container notification-channel {
      config false;
      uses ncs_rpc_notif_notification-channel;
      description
        "none";
    }
    container subscription-filter {
      uses ncs_rpc_notif_subscription-filter;
      description
        "none";
    }
    leaf subscription-state {
      type ncs_rpc_notif_subscription-state;
      description
        "none";
    }
    leaf-list supported-notification-types {
      type ncs_rpc_notif_notification-type;
      config false;
      min-elements 1;
      description
        "none";
    }
    leaf-list supported-object-types {
      type ncs_rpc_notif_object-type;
      config false;
      min-elements 1;
      description
        "none";
    }
    uses tapi-common:ncs_rpc_notif_service-spec;
    description
      "none";
  }

  grouping ncs_rpc_notif_subscription-filter {
    leaf-list requested-notification-types {
      type ncs_rpc_notif_notification-type;
      description
        "none";
    }
    leaf-list requested-object-types {
      type ncs_rpc_notif_object-type;
      description
        "none";
    }
    leaf-list requested-layer-protocols {
      type tapi-common:ncs_rpc_notif_layer-protocol-name;
      description
        "none";
    }
    leaf-list requested-object-identifier {
      type tapi-common:ncs_rpc_notif_uuid;
      description
        "none";
    }
    leaf include-content {
      type boolean;
      description
        "Indicates whether the published Notification includes content or just the Notification Id (which enables retrieval of the notification at the later stage)";
    }
    uses tapi-common:ncs_rpc_notif_local-class;
    description
      "none";
  }

  grouping ncs_rpc_notif_notification {
    leaf notification-type {
      type ncs_rpc_notif_notification-type;
      description
        "none";
    }
    leaf target-object-type {
      type ncs_rpc_notif_object-type;
      description
        "none";
    }
    leaf target-object-identifier {
      type tapi-common:ncs_rpc_notif_uuid;
      description
        "none";
    }
    list target-object-name {
      key "value-name";
      min-elements 1;
      uses tapi-common:ncs_rpc_notif_name-and-value;
      description
        "none";
    }
    leaf event-time-stamp {
      type tapi-common:ncs_rpc_notif_date-and-time;
      description
        "none";
    }
    leaf sequence-number {
      type uint64;
      config false;
      description
        "A monotonous increasing sequence number associated with the notification.
         The exact semantics of how this sequence number is assigned (per channel or subscription or source or system) is left undefined.";
    }
    leaf source-indicator {
      type ncs_rpc_notif_source-indicator;
      description
        "none";
    }
    leaf layer-protocol-name {
      type tapi-common:ncs_rpc_notif_layer-protocol-name;
      description
        "none";
    }
    list changed-attributes {
      key "value-name";
      uses ncs_rpc_notif_name-and-value-change;
      description
        "none";
    }
    list additional-info {
      key "value-name";
      uses tapi-common:ncs_rpc_notif_name-and-value;
      description
        "none";
    }
    leaf additional-text {
      type string;
      description
        "none";
    }
    container tca-info {
      uses ncs_rpc_notif_tca-info;
      description
        "none";
    }
    container alarm-info {
      uses ncs_rpc_notif_alarm-info;
      description
        "none";
    }
    uses tapi-common:ncs_rpc_notif_resource-spec;
    description
      "none";
  }

  grouping ncs_rpc_notif_notification-channel {
    leaf stream-address {
      type string;
      config false;
      description
        "The address/location/URI of the channel/stream to which the subscribed notifications are published.
         This specifics of this is typically dependent on the implementation protocol & mechanism and hence is typed as a string.";
    }
    leaf next-sequence-no {
      type uint64;
      config false;
      description
        "The sequence number of the next notification that will be published on the channel";
    }
    uses tapi-common:ncs_rpc_notif_local-class;
    description
      "none";
  }

  grouping ncs_rpc_notif_notification-context {
    list notif-subscription {
      key "uuid";
      uses ncs_rpc_notif_notification-subscription-service;
      description
        "none";
    }
    list notification {
      key "uuid";
      config false;
      uses ncs_rpc_notif_notification;
      description
        "none";
    }
    description
      "none";
  }

  grouping ncs_rpc_notif_alarm-info {
    leaf is-transient {
      type boolean;
      config false;
      description
        "none";
    }
    leaf perceived-severity {
      type ncs_rpc_notif_perceived-severity-type;
      config false;
      description
        "none";
    }
    leaf probable-cause {
      type string;
      config false;
      description
        "none";
    }
    leaf service-affecting {
      type ncs_rpc_notif_service-affecting;
      description
        "none";
    }
    description
      "none";
  }

  grouping ncs_rpc_notif_tca-info {
    leaf is-transient {
      type boolean;
      config false;
      description
        "none";
    }
    leaf threshold-crossing {
      type ncs_rpc_notif_threshold-crossing-type;
      description
        "none";
    }
    leaf threshold-parameter {
      type string;
      config false;
      description
        "none";
    }
    leaf threshold-value {
      type uint64;
      config false;
      description
        "none";
    }
    leaf perceived-severity {
      type ncs_rpc_notif_perceived-tca-severity;
      description
        "none";
    }
    leaf measurement-interval {
      type tapi-common:ncs_rpc_notif_date-and-time;
      description
        "none";
    }
    leaf suspect-interval-flag {
      type boolean;
      description
        "none";
    }
    description
      "none";
  }

  grouping ncs_rpc_notif_name-and-value-change {
    leaf value-name {
      type string;
      description
        "The name of the value. The value need not have a name.";
    }
    leaf old-value {
      type string;
      description
        "The value";
    }
    leaf new-value {
      type string;
      description
        "The value";
    }
    description
      "A scoped name-value triple, including old value and new value";
  }

  grouping live_ncs_notification-subscription-service {
    list notification {
      key "uuid";
      uses live_ncs_notification;
      description
        "none";
    }
    container notification-channel {
      uses live_ncs_notification-channel;
      description
        "none";
    }
    container subscription-filter {
      uses live_ncs_subscription-filter;
      description
        "none";
    }
    leaf subscription-state {
      type live_ncs_subscription-state;
      description
        "none";
    }
    leaf-list supported-notification-types {
      type live_ncs_notification-type;
      // NCS drop min-elements statement
      description
        "none";
    }
    leaf-list supported-object-types {
      type live_ncs_object-type;
      // NCS drop min-elements statement
      description
        "none";
    }
    uses tapi-common:live_ncs_service-spec;
    description
      "none";
  }

  grouping live_ncs_subscription-filter {
    leaf-list requested-notification-types {
      type live_ncs_notification-type;
      description
        "none";
    }
    leaf-list requested-object-types {
      type live_ncs_object-type;
      description
        "none";
    }
    leaf-list requested-layer-protocols {
      type tapi-common:live_ncs_layer-protocol-name;
      description
        "none";
    }
    leaf-list requested-object-identifier {
      type tapi-common:live_ncs_uuid;
      description
        "none";
    }
    leaf include-content {
      type boolean;
      description
        "Indicates whether the published Notification includes content or just the Notification Id (which enables retrieval of the notification at the later stage)";
    }
    uses tapi-common:live_ncs_local-class;
    description
      "none";
  }

  grouping live_ncs_notification {
    leaf notification-type {
      type live_ncs_notification-type;
      description
        "none";
    }
    leaf target-object-type {
      type live_ncs_object-type;
      description
        "none";
    }
    leaf target-object-identifier {
      type tapi-common:live_ncs_uuid;
      description
        "none";
    }
    list target-object-name {
      key "value-name";
      // NCS drop min-elements statement
      uses tapi-common:live_ncs_name-and-value;
      description
        "none";
    }
    leaf event-time-stamp {
      type tapi-common:live_ncs_date-and-time;
      description
        "none";
    }
    leaf sequence-number {
      type uint64;
      description
        "A monotonous increasing sequence number associated with the notification.
         The exact semantics of how this sequence number is assigned (per channel or subscription or source or system) is left undefined.";
    }
    leaf source-indicator {
      type live_ncs_source-indicator;
      description
        "none";
    }
    leaf layer-protocol-name {
      type tapi-common:live_ncs_layer-protocol-name;
      description
        "none";
    }
    list changed-attributes {
      key "value-name";
      uses live_ncs_name-and-value-change;
      description
        "none";
    }
    list additional-info {
      key "value-name";
      uses tapi-common:live_ncs_name-and-value;
      description
        "none";
    }
    leaf additional-text {
      type string;
      description
        "none";
    }
    container tca-info {
      uses live_ncs_tca-info;
      description
        "none";
    }
    container alarm-info {
      uses live_ncs_alarm-info;
      description
        "none";
    }
    uses tapi-common:live_ncs_resource-spec;
    description
      "none";
  }

  grouping live_ncs_notification-channel {
    leaf stream-address {
      type string;
      description
        "The address/location/URI of the channel/stream to which the subscribed notifications are published.
         This specifics of this is typically dependent on the implementation protocol & mechanism and hence is typed as a string.";
    }
    leaf next-sequence-no {
      type uint64;
      description
        "The sequence number of the next notification that will be published on the channel";
    }
    uses tapi-common:live_ncs_local-class;
    description
      "none";
  }

  grouping live_ncs_notification-context {
    list notif-subscription {
      key "uuid";
      uses live_ncs_notification-subscription-service;
      description
        "none";
    }
    list notification {
      key "uuid";
      uses live_ncs_notification;
      description
        "none";
    }
    description
      "none";
  }

  grouping live_ncs_alarm-info {
    leaf is-transient {
      type boolean;
      description
        "none";
    }
    leaf perceived-severity {
      type live_ncs_perceived-severity-type;
      description
        "none";
    }
    leaf probable-cause {
      type string;
      description
        "none";
    }
    leaf service-affecting {
      type live_ncs_service-affecting;
      description
        "none";
    }
    description
      "none";
  }

  grouping live_ncs_tca-info {
    leaf is-transient {
      type boolean;
      description
        "none";
    }
    leaf threshold-crossing {
      type live_ncs_threshold-crossing-type;
      description
        "none";
    }
    leaf threshold-parameter {
      type string;
      description
        "none";
    }
    leaf threshold-value {
      type uint64;
      description
        "none";
    }
    leaf perceived-severity {
      type live_ncs_perceived-tca-severity;
      description
        "none";
    }
    leaf measurement-interval {
      type tapi-common:live_ncs_date-and-time;
      description
        "none";
    }
    leaf suspect-interval-flag {
      type boolean;
      description
        "none";
    }
    description
      "none";
  }

  grouping live_ncs_name-and-value-change {
    leaf value-name {
      type string;
      description
        "The name of the value. The value need not have a name.";
    }
    leaf old-value {
      type string;
      description
        "The value";
    }
    leaf new-value {
      type string;
      description
        "The value";
    }
    description
      "A scoped name-value triple, including old value and new value";
  }

  grouping notification-subscription-service {
    // NCS drop config false list notification
    // NCS drop config false container 'notification-channel'
    container subscription-filter {
      uses subscription-filter;
      description
        "none";
    }
    leaf subscription-state {
      type subscription-state;
      description
        "none";
    }
    // NCS drop config false leaf-list 'supported-notification-types'
    // NCS drop config false leaf-list 'supported-object-types'
    uses tapi-common:service-spec;
    description
      "none";
  }

  grouping subscription-filter {
    leaf-list requested-notification-types {
      type notification-type;
      description
        "none";
    }
    leaf-list requested-object-types {
      type object-type;
      description
        "none";
    }
    leaf-list requested-layer-protocols {
      type tapi-common:layer-protocol-name;
      description
        "none";
    }
    leaf-list requested-object-identifier {
      type tapi-common:uuid;
      description
        "none";
    }
    leaf include-content {
      type boolean;
      description
        "Indicates whether the published Notification includes content or just the Notification Id (which enables retrieval of the notification at the later stage)";
    }
    uses tapi-common:local-class;
    description
      "none";
  }

  grouping notification {
    leaf notification-type {
      type notification-type;
      description
        "none";
    }
    leaf target-object-type {
      type object-type;
      description
        "none";
    }
    leaf target-object-identifier {
      type tapi-common:uuid;
      description
        "none";
    }
    list target-object-name {
      key "value-name";
      min-elements 1;
      uses tapi-common:name-and-value;
      description
        "none";
    }
    leaf event-time-stamp {
      type tapi-common:date-and-time;
      description
        "none";
    }
    // NCS drop config false leaf 'sequence-number'
    leaf source-indicator {
      type source-indicator;
      description
        "none";
    }
    leaf layer-protocol-name {
      type tapi-common:layer-protocol-name;
      description
        "none";
    }
    list changed-attributes {
      key "value-name";
      uses name-and-value-change;
      description
        "none";
    }
    list additional-info {
      key "value-name";
      uses tapi-common:name-and-value;
      description
        "none";
    }
    leaf additional-text {
      type string;
      description
        "none";
    }
    container tca-info {
      uses tca-info;
      description
        "none";
    }
    container alarm-info {
      uses alarm-info;
      description
        "none";
    }
    uses tapi-common:resource-spec;
    description
      "none";
  }

  grouping notification-channel {
    // NCS drop config false leaf 'stream-address'
    // NCS drop config false leaf 'next-sequence-no'
    uses tapi-common:local-class;
    description
      "none";
  }

  grouping notification-context {
    list notif-subscription {
      key "uuid";
      uses notification-subscription-service;
      description
        "none";
    }
    // NCS drop config false list notification
    description
      "none";
  }

  grouping alarm-info {
    // NCS drop config false leaf 'is-transient'
    // NCS drop config false leaf 'perceived-severity'
    // NCS drop config false leaf 'probable-cause'
    leaf service-affecting {
      type service-affecting;
      description
        "none";
    }
    description
      "none";
  }

  grouping tca-info {
    // NCS drop config false leaf 'is-transient'
    leaf threshold-crossing {
      type threshold-crossing-type;
      description
        "none";
    }
    // NCS drop config false leaf 'threshold-parameter'
    // NCS drop config false leaf 'threshold-value'
    leaf perceived-severity {
      type perceived-tca-severity;
      description
        "none";
    }
    leaf measurement-interval {
      type tapi-common:date-and-time;
      description
        "none";
    }
    leaf suspect-interval-flag {
      type boolean;
      description
        "none";
    }
    description
      "none";
  }

  grouping name-and-value-change {
    leaf value-name {
      type string;
      description
        "The name of the value. The value need not have a name.";
    }
    leaf old-value {
      type string;
      description
        "The value";
    }
    leaf new-value {
      type string;
      description
        "The value";
    }
    description
      "A scoped name-value triple, including old value and new value";
  }

  augment "/ncs:devices/ncs:device/ncs:rpc" {
    container rpc-get-notification-list {
      tailf:ncs-device-type "netconf";
      tailf:display-when "not(../../ncs:module) or ../../ncs:module[ncs:name='tapi-notification']";
      tailf:action get-notification-list {
        tailf:actionpoint ncsproxy {
          tailf:internal;
        }
        description
          "none";
        input {
          leaf subscription-id-or-name {
            type string;
            description
              "none";
          }
          leaf time-period {
            type string;
            description
              "none";
          }
        }
        output {
          list notification {
            key "uuid";
            uses ncs_rpc_notif_notification;
            description
              "none";
          }
        }
      }
    }
  }
  augment "/ncs:devices/ncs:device-group/ncs:ned-id/ncs:rpc" {
    container rpc-get-notification-list {
      tailf:ncs-device-type "netconf";
      tailf:display-when "../../ncs:id = 'onf-tapi-nc-2.0:onf-tapi-nc-2.0'";
      tailf:action get-notification-list {
        tailf:actionpoint ncsproxy {
          tailf:internal;
        }
        description
          "none";
        input {
          leaf subscription-id-or-name {
            type string;
            description
              "none";
          }
          leaf time-period {
            type string;
            description
              "none";
          }
        }
        output {
          container "device" {
            leaf "name" {
              type string;
            }
            leaf "info" {
              type string;
            }
            container "result" {
              list notification {
                key "uuid";
                uses ncs_rpc_notif_notification;
                description
                  "none";
              }
            }
          }
        }
      }
    }
  }
  augment "/ncs:devices/ncs:device/ncs:rpc" {
    container rpc-get-notification-subscription-service-list {
      tailf:ncs-device-type "netconf";
      tailf:display-when "not(../../ncs:module) or ../../ncs:module[ncs:name='tapi-notification']";
      tailf:action get-notification-subscription-service-list {
        tailf:actionpoint ncsproxy {
          tailf:internal;
        }
        description
          "none";
        output {
          list subscription-service {
            key "uuid";
            uses ncs_rpc_notif_notification-subscription-service;
            description
              "none";
          }
        }
      }
    }
  }
  augment "/ncs:devices/ncs:device-group/ncs:ned-id/ncs:rpc" {
    container rpc-get-notification-subscription-service-list {
      tailf:ncs-device-type "netconf";
      tailf:display-when "../../ncs:id = 'onf-tapi-nc-2.0:onf-tapi-nc-2.0'";
      tailf:action get-notification-subscription-service-list {
        tailf:actionpoint ncsproxy {
          tailf:internal;
        }
        description
          "none";
        output {
          container "device" {
            leaf "name" {
              type string;
            }
            leaf "info" {
              type string;
            }
            container "result" {
              list subscription-service {
                key "uuid";
                uses ncs_rpc_notif_notification-subscription-service;
                description
                  "none";
              }
            }
          }
        }
      }
    }
  }
  augment "/ncs:devices/ncs:device/ncs:rpc" {
    container rpc-get-notification-subscription-service-details {
      tailf:ncs-device-type "netconf";
      tailf:display-when "not(../../ncs:module) or ../../ncs:module[ncs:name='tapi-notification']";
      tailf:action get-notification-subscription-service-details {
        tailf:actionpoint ncsproxy {
          tailf:internal;
        }
        description
          "none";
        input {
          leaf subscription-id-or-name {
            type string;
            description
              "none";
          }
        }
        output {
          container subscription-service {
            uses ncs_rpc_notif_notification-subscription-service;
            description
              "none";
          }
        }
      }
    }
  }
  augment "/ncs:devices/ncs:device-group/ncs:ned-id/ncs:rpc" {
    container rpc-get-notification-subscription-service-details {
      tailf:ncs-device-type "netconf";
      tailf:display-when "../../ncs:id = 'onf-tapi-nc-2.0:onf-tapi-nc-2.0'";
      tailf:action get-notification-subscription-service-details {
        tailf:actionpoint ncsproxy {
          tailf:internal;
        }
        description
          "none";
        input {
          leaf subscription-id-or-name {
            type string;
            description
              "none";
          }
        }
        output {
          container "device" {
            leaf "name" {
              type string;
            }
            leaf "info" {
              type string;
            }
            container "result" {
              container subscription-service {
                uses ncs_rpc_notif_notification-subscription-service;
                description
                  "none";
              }
            }
          }
        }
      }
    }
  }
  augment "/ncs:devices/ncs:device/ncs:rpc" {
    container rpc-delete-notification-subscription-service {
      tailf:ncs-device-type "netconf";
      tailf:display-when "not(../../ncs:module) or ../../ncs:module[ncs:name='tapi-notification']";
      tailf:action delete-notification-subscription-service {
        tailf:actionpoint ncsproxy {
          tailf:internal;
        }
        description
          "none";
        input {
          leaf subscription-id-or-name {
            type string;
            description
              "none";
          }
        }
        output {
          container subscription-service {
            uses ncs_rpc_notif_notification-subscription-service;
            description
              "none";
          }
        }
      }
    }
  }
  augment "/ncs:devices/ncs:device-group/ncs:ned-id/ncs:rpc" {
    container rpc-delete-notification-subscription-service {
      tailf:ncs-device-type "netconf";
      tailf:display-when "../../ncs:id = 'onf-tapi-nc-2.0:onf-tapi-nc-2.0'";
      tailf:action delete-notification-subscription-service {
        tailf:actionpoint ncsproxy {
          tailf:internal;
        }
        description
          "none";
        input {
          leaf subscription-id-or-name {
            type string;
            description
              "none";
          }
        }
        output {
          container "device" {
            leaf "name" {
              type string;
            }
            leaf "info" {
              type string;
            }
            container "result" {
              container subscription-service {
                uses ncs_rpc_notif_notification-subscription-service;
                description
                  "none";
              }
            }
          }
        }
      }
    }
  }
  augment "/ncs:devices/ncs:device/ncs:rpc" {
    container rpc-update-notification-subscription-service {
      tailf:ncs-device-type "netconf";
      tailf:display-when "not(../../ncs:module) or ../../ncs:module[ncs:name='tapi-notification']";
      tailf:action update-notification-subscription-service {
        tailf:actionpoint ncsproxy {
          tailf:internal;
        }
        description
          "none";
        input {
          leaf subscription-id-or-name {
            type string;
            description
              "none";
          }
          container subscription-filter {
            uses ncs_rpc_notif_subscription-filter;
            description
              "none";
          }
          leaf subscription-state {
            type ncs_rpc_notif_subscription-state;
            description
              "none";
          }
        }
        output {
          container subscription-service {
            uses ncs_rpc_notif_notification-subscription-service;
            description
              "none";
          }
        }
      }
    }
  }
  augment "/ncs:devices/ncs:device-group/ncs:ned-id/ncs:rpc" {
    container rpc-update-notification-subscription-service {
      tailf:ncs-device-type "netconf";
      tailf:display-when "../../ncs:id = 'onf-tapi-nc-2.0:onf-tapi-nc-2.0'";
      tailf:action update-notification-subscription-service {
        tailf:actionpoint ncsproxy {
          tailf:internal;
        }
        description
          "none";
        input {
          leaf subscription-id-or-name {
            type string;
            description
              "none";
          }
          container subscription-filter {
            uses ncs_rpc_notif_subscription-filter;
            description
              "none";
          }
          leaf subscription-state {
            type ncs_rpc_notif_subscription-state;
            description
              "none";
          }
        }
        output {
          container "device" {
            leaf "name" {
              type string;
            }
            leaf "info" {
              type string;
            }
            container "result" {
              container subscription-service {
                uses ncs_rpc_notif_notification-subscription-service;
                description
                  "none";
              }
            }
          }
        }
      }
    }
  }
  augment "/ncs:devices/ncs:device/ncs:rpc" {
    container rpc-create-notification-subscription-service {
      tailf:ncs-device-type "netconf";
      tailf:display-when "not(../../ncs:module) or ../../ncs:module[ncs:name='tapi-notification']";
      tailf:action create-notification-subscription-service {
        tailf:actionpoint ncsproxy {
          tailf:internal;
        }
        description
          "none";
        input {
          container subscription-filter {
            uses ncs_rpc_notif_subscription-filter;
            description
              "none";
          }
          leaf subscription-state {
            type ncs_rpc_notif_subscription-state;
            description
              "none";
          }
        }
        output {
          container subscription-service {
            uses ncs_rpc_notif_notification-subscription-service;
            description
              "none";
          }
        }
      }
    }
  }
  augment "/ncs:devices/ncs:device-group/ncs:ned-id/ncs:rpc" {
    container rpc-create-notification-subscription-service {
      tailf:ncs-device-type "netconf";
      tailf:display-when "../../ncs:id = 'onf-tapi-nc-2.0:onf-tapi-nc-2.0'";
      tailf:action create-notification-subscription-service {
        tailf:actionpoint ncsproxy {
          tailf:internal;
        }
        description
          "none";
        input {
          container subscription-filter {
            uses ncs_rpc_notif_subscription-filter;
            description
              "none";
          }
          leaf subscription-state {
            type ncs_rpc_notif_subscription-state;
            description
              "none";
          }
        }
        output {
          container "device" {
            leaf "name" {
              type string;
            }
            leaf "info" {
              type string;
            }
            container "result" {
              container subscription-service {
                uses ncs_rpc_notif_notification-subscription-service;
                description
                  "none";
              }
            }
          }
        }
      }
    }
  }
  augment "/ncs:devices/ncs:device/ncs:rpc" {
    container rpc-get-supported-notification-types {
      tailf:ncs-device-type "netconf";
      tailf:display-when "not(../../ncs:module) or ../../ncs:module[ncs:name='tapi-notification']";
      tailf:action get-supported-notification-types {
        tailf:actionpoint ncsproxy {
          tailf:internal;
        }
        description
          "none";
        output {
          leaf-list supported-notification-types {
            type ncs_rpc_notif_notification-type;
            min-elements 1;
            description
              "none";
          }
          leaf-list supported-object-types {
            type ncs_rpc_notif_object-type;
            min-elements 1;
            description
              "none";
          }
        }
      }
    }
  }
  augment "/ncs:devices/ncs:device-group/ncs:ned-id/ncs:rpc" {
    container rpc-get-supported-notification-types {
      tailf:ncs-device-type "netconf";
      tailf:display-when "../../ncs:id = 'onf-tapi-nc-2.0:onf-tapi-nc-2.0'";
      tailf:action get-supported-notification-types {
        tailf:actionpoint ncsproxy {
          tailf:internal;
        }
        description
          "none";
        output {
          container "device" {
            leaf "name" {
              type string;
            }
            leaf "info" {
              type string;
            }
            container "result" {
              leaf-list supported-notification-types {
                type ncs_rpc_notif_notification-type;
                min-elements 1;
                description
                  "none";
              }
              leaf-list supported-object-types {
                type ncs_rpc_notif_object-type;
                min-elements 1;
                description
                  "none";
              }
            }
          }
        }
      }
    }
  }
  augment "/ncs:devices/ncs:device/ncs:notifications/ncs:received-notifications/ncs:notification/ncs:data" {
    container notification {
      presence "";
      config false;
      uses ncs_rpc_notif_notification;
      description
        "none";
    }
  }
  augment "/ncs:devices/ncs:device/ncs:netconf-notifications/ncs:received-notifications/ncs:notification/ncs:data" {
    container notification {
      presence "";
      config false;
      uses ncs_rpc_notif_notification;
      description
        "none";
    }
  }
  augment "/ncs:devices/ncs:template/ncs:ned-id/ncs:config/tapi-common:context" {
    container notification-context {
      uses ncs_template_notification-context;
      description
        "Augments the base TAPI Context with NotificationService information";
    }
    description
      "Augments the base TAPI Context with NotificationService information";
  }
  augment "/ncs:devices/ncs:device/ncs:live-status/tapi-common:context" {
    container notification-context {
      tailf:ncs-device-type "netconf";
      tailf:display-when "not(../../../ncs:module) or ../../../ncs:module[ncs:name='tapi-notification'] or (../../../ncs:live-status-protocol[not(ncs:capability)]) or (../../../ncs:live-status-protocol/ncs:capability/ncs:module[.='tapi-notification'])";
      uses live_ncs_notification-context;
      description
        "Augments the base TAPI Context with NotificationService information";
    }
    description
      "Augments the base TAPI Context with NotificationService information";
  }
  augment "/ncs:devices/ncs:device/ncs:config/tapi-common:context" {
    container notification-context {
      tailf:ncs-device-type "netconf";
      tailf:display-when "not(../../../ncs:module) or ../../../ncs:module[ncs:name='tapi-notification']";
      uses notification-context;
      description
        "Augments the base TAPI Context with NotificationService information";
    }
    description
      "Augments the base TAPI Context with NotificationService information";
  }
}
