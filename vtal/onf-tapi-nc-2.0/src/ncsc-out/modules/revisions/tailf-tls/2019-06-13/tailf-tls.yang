module tailf-tls {
  // Generated by yanger -t ncs
  tailf:mount-id "onf-tapi-nc-2.0:onf-tapi-nc-2.0";
  tailf:ncs-device-type "netconf";

  yang-version 1.1;
  namespace "http://tail-f.com/ns/tls";
  prefix tls;

  import ietf-netconf-acm {
    prefix nacm;
  }
  import ietf-x509-cert-to-name {
    prefix x509c2n;
  }
  import ietf-yang-types {
    prefix yang;
  }
  import tailf-common {
    prefix tailf;
  }
  import tailf-ncs {
    prefix ncs;
  }

  organization
    "Tail-f Systems";
  description
    "This module contains configuration items for TLS key storage for HTTP
     based protocols, i.e. Web UI and RESTCONF.

     If the webui ssl transport conf section is enabled and configured to fetch
     TLS data from the database, the web server fetch these values upon start
     or reload. For further details see the Web UI chapter Web server section
     TLS data in database.

     Copyright 2019 Cisco Systems, Inc.
     All rights reserved.
     Permission is hereby granted to redistribute this file without
     modification.";

  revision 2019-06-13 {
    description
      "Initial revision, released as part of ConfD-7.3 / NCS-5.3.";
  }

  typedef ncs_template_tls-private-key {
    type string;
  }

  typedef ncs_template_tls-certificate {
    type string;
  }

  typedef ncs_template_tls-ca-certificate {
    type string;
  }

  typedef ncs_rpc_notif_tls-private-key {
    tailf:info
      "TLS Privaty Key";
    type tailf:aes-cfb-128-encrypted-string;
  }

  typedef ncs_rpc_notif_tls-certificate {
    tailf:info
      "TLS Public Key Certificate";
    type binary;
  }

  typedef ncs_rpc_notif_tls-ca-certificate {
    tailf:info
      "TLS CA Certificate";
    type binary;
  }

  typedef live_ncs_tls-private-key {
    tailf:info
      "TLS Privaty Key";
    type tailf:aes-cfb-128-encrypted-string;
  }

  typedef live_ncs_tls-certificate {
    tailf:info
      "TLS Public Key Certificate";
    type binary;
  }

  typedef live_ncs_tls-ca-certificate {
    tailf:info
      "TLS CA Certificate";
    type binary;
  }

  typedef tls-private-key {
    tailf:info
      "TLS Privaty Key";
    type tailf:aes-cfb-128-encrypted-string;
  }

  typedef tls-certificate {
    tailf:info
      "TLS Public Key Certificate";
    type binary;
  }

  typedef tls-ca-certificate {
    tailf:info
      "TLS CA Certificate";
    type binary;
  }

  augment "/ncs:devices/ncs:device/ncs:config" {
    container tls {
      tailf:ncs-device-type "netconf";
      tailf:display-when "not(../../ncs:module) or ../../ncs:module[ncs:name='tailf-tls']";
      presence "";
      nacm:default-deny-all;
      tailf:info
        "Global TLS keystore configuration";
      tailf:code-name "tls_container";
      container private-key {
        leaf key-data {
          type tls-private-key;
          mandatory true;
          // NCS drop tailf:typepoint
          tailf:cli-multi-line-prompt;
          // NCS drop tailf:validate
          description
            "The binary data for the private key, in PEM format (text starting
             with '-----BEGIN ...-----'). If the key is encrypted, the
             passphrase for the key must be configured via 'passphrase'.

             Encrypted keys must be in PKCS#1 format and supported encryption
             algorithms are: RC2-CBC, DES-CBC, DES-EDE3-CBC, and AES-128-CBC.

             If the key is not encrypted both PKCS#1 and PKCS#8 formats can be
             used.";
        }
        leaf passphrase {
          tailf:ned-ignore-compare-config;
          tailf:info
            "Passphrase for key";
          type tailf:aes-cfb-128-encrypted-string;
          tailf:suppress-echo true;
          description
            "The value of this leaf is used as passphrase for the key if
             it is encrypted.";
        }
      }
      container certificate {
        leaf cert-data {
          type tls-certificate;
          mandatory true;
          // NCS drop tailf:typepoint
          tailf:cli-multi-line-prompt;
          // NCS drop tailf:validate
          description
            "The binary data for the public key certificate, in PEM format
             (text starting with '-----BEGIN ...-----').";
        }
        // NCS drop config false leaf fingerprint
      }
      list ca-certificates {
        key "name";
        leaf name {
          type string;
        }
        leaf cacert-data {
          type tls-ca-certificate;
          // NCS drop tailf:typepoint
          tailf:cli-multi-line-prompt;
          // NCS drop tailf:validate
          description
            "The binary data for the CA certificate, in PEM format (text starting
             with '-----BEGIN ...-----').";
        }
        // NCS drop config false leaf fingerprint
      }
    }
  }
  augment "/ncs:devices/ncs:device/ncs:live-status" {
    container tls {
      tailf:ncs-device-type "netconf";
      tailf:display-when "not(../../ncs:module) or ../../ncs:module[ncs:name='tailf-tls'] or (../../ncs:live-status-protocol[not(ncs:capability)]) or (../../ncs:live-status-protocol/ncs:capability/ncs:module[.='tailf-tls'])";
      presence "";
      nacm:default-deny-all;
      tailf:info
        "Global TLS keystore configuration";
      tailf:code-name "tls_container";
      container private-key {
        leaf key-data {
          type live_ncs_tls-private-key;
          // NCS drop mandatory statement
          // NCS drop tailf:typepoint
          // NCS drop tailf:cli-multi-line-prompt
          // NCS drop tailf:validate
          description
            "The binary data for the private key, in PEM format (text starting
             with '-----BEGIN ...-----'). If the key is encrypted, the
             passphrase for the key must be configured via 'passphrase'.

             Encrypted keys must be in PKCS#1 format and supported encryption
             algorithms are: RC2-CBC, DES-CBC, DES-EDE3-CBC, and AES-128-CBC.

             If the key is not encrypted both PKCS#1 and PKCS#8 formats can be
             used.";
        }
        leaf passphrase {
          tailf:info
            "Passphrase for key";
          type tailf:aes-cfb-128-encrypted-string;
          tailf:suppress-echo true;
          description
            "The value of this leaf is used as passphrase for the key if
             it is encrypted.";
        }
      }
      container certificate {
        leaf cert-data {
          type live_ncs_tls-certificate;
          // NCS drop mandatory statement
          // NCS drop tailf:typepoint
          // NCS drop tailf:cli-multi-line-prompt
          // NCS drop tailf:validate
          description
            "The binary data for the public key certificate, in PEM format
             (text starting with '-----BEGIN ...-----').";
        }
        leaf fingerprint {
          type x509c2n:live_ncs_tls-fingerprint;
          // NCS drop tailf:callpoint
          tailf:info
            "SHA256 fingerprint of certificate.";
          description
            "SHA256 fingerprint of certificate. NB! First octet represents which
             hash algorithm is used, i.e. SHA256 (0x04),
             see x509c2n:tls-fingerprint.";
        }
      }
      list ca-certificates {
        key "name";
        leaf name {
          type string;
        }
        leaf cacert-data {
          type live_ncs_tls-ca-certificate;
          // NCS drop tailf:typepoint
          // NCS drop tailf:cli-multi-line-prompt
          // NCS drop tailf:validate
          description
            "The binary data for the CA certificate, in PEM format (text starting
             with '-----BEGIN ...-----').";
        }
        leaf fingerprint {
          type x509c2n:live_ncs_tls-fingerprint;
          // NCS drop tailf:callpoint
          tailf:info
            "SHA256 fingerprint of CA certificate.";
          description
            "SHA256 fingerprint of CA certificate. NB! First octet represents
             which hash algorithm is used, i.e. SHA256 (0x04), see
             x509c2n:tls-fingerprint.";
        }
      }
    }
  }
  augment "/ncs:devices/ncs:template/ncs:ned-id/ncs:config" {
    container tls {
      presence "";
      nacm:default-deny-all;
      tailf:code-name "tls_container";
      container private-key {
        leaf key-data {
          type ncs_template_tls-private-key;
          // NCS drop mandatory statement
          description
            "The binary data for the private key, in PEM format (text starting
             with '-----BEGIN ...-----'). If the key is encrypted, the
             passphrase for the key must be configured via 'passphrase'.

             Encrypted keys must be in PKCS#1 format and supported encryption
             algorithms are: RC2-CBC, DES-CBC, DES-EDE3-CBC, and AES-128-CBC.

             If the key is not encrypted both PKCS#1 and PKCS#8 formats can be
             used.";
        }
        leaf passphrase {
          type string;
          description
            "The value of this leaf is used as passphrase for the key if
             it is encrypted.";
        }
      }
      container certificate {
        leaf cert-data {
          type ncs_template_tls-certificate;
          // NCS drop mandatory statement
          description
            "The binary data for the public key certificate, in PEM format
             (text starting with '-----BEGIN ...-----').";
        }
        // NCS drop config false leaf fingerprint
      }
      list ca-certificates {
        // NCS patched for predictable order
        ordered-by user;
        key "name";
        leaf name {
          type string;
        }
        leaf cacert-data {
          type ncs_template_tls-ca-certificate;
          description
            "The binary data for the CA certificate, in PEM format (text starting
             with '-----BEGIN ...-----').";
        }
        // NCS drop config false leaf fingerprint
      }
    }
  }
}
