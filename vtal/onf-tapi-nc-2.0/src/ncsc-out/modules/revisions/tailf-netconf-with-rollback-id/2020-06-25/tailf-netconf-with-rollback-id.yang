module tailf-netconf-with-rollback-id {
  // Generated by yanger -t ncs
  tailf:mount-id "onf-tapi-nc-2.0:onf-tapi-nc-2.0";
  tailf:ncs-device-type "netconf";

  yang-version 1.1;
  namespace "http://tail-f.com/ns/netconf/with-rollback-id";
  prefix wrbid;

  import ietf-netconf {
    prefix nc;
  }
  import tailf-netconf-transactions {
    prefix tr;
  }
  import tailf-rollback {
    prefix rollback;
  }
  import tailf-common {
    prefix tailf;
  }
  import tailf-ncs {
    prefix ncs;
  }

  description
    "This module adds a parameter 'with-rollback-id' to the
     following rpcs:

       o  edit-config
       o  copy-config
       o  commit
       o  commit-transaction

     This parameter lets the client request that the id of the generate
     rollback file is returned in the reply to the request.

     Copyright 2020 Cisco Systems, Inc.
     All rights reserved.
     Permission is hereby granted to redistribute this file without
     modification.";

  revision 2020-06-25 {
    description
      "Initial revision.";
  }

  grouping ncs_template_with-rollback-id-params {
    leaf with-rollback-id {
      type empty;
    }
  }

  grouping ncs_template_with-rollback-id-reply {
    uses rollback:ncs_template_rollback-commit-result;
  }

  grouping ncs_rpc_notif_with-rollback-id-params {
    leaf with-rollback-id {
      type empty;
    }
  }

  grouping ncs_rpc_notif_with-rollback-id-reply {
    uses rollback:ncs_rpc_notif_rollback-commit-result;
  }

  grouping live_ncs_with-rollback-id-params {
    leaf with-rollback-id {
      type empty;
    }
  }

  grouping live_ncs_with-rollback-id-reply {
    uses rollback:live_ncs_rollback-commit-result;
  }

  grouping with-rollback-id-params {
    leaf with-rollback-id {
      type empty;
    }
  }

  grouping with-rollback-id-reply {
    uses rollback:rollback-commit-result;
  }

  augment "/ncs:devices/ncs:device/ncs:rpc/nc:rpc-edit-config/nc:edit-config/nc:input" {
    uses ncs_rpc_notif_with-rollback-id-params;
  }
  augment "/ncs:devices/ncs:device/ncs:rpc/nc:rpc-edit-config/nc:edit-config/nc:output" {
    uses ncs_rpc_notif_with-rollback-id-reply;
  }
  augment "/ncs:devices/ncs:device/ncs:rpc/nc:rpc-copy-config/nc:copy-config/nc:input" {
    uses ncs_rpc_notif_with-rollback-id-params;
  }
  augment "/ncs:devices/ncs:device/ncs:rpc/nc:rpc-copy-config/nc:copy-config/nc:output" {
    uses ncs_rpc_notif_with-rollback-id-reply;
  }
  augment "/ncs:devices/ncs:device/ncs:rpc/nc:rpc-commit/nc:commit/nc:input" {
    uses ncs_rpc_notif_with-rollback-id-params;
  }
  augment "/ncs:devices/ncs:device/ncs:rpc/nc:rpc-commit/nc:commit/nc:output" {
    uses ncs_rpc_notif_with-rollback-id-reply;
  }
  augment "/ncs:devices/ncs:device/ncs:rpc/tr:rpc-commit-transaction/tr:commit-transaction/tr:input" {
    uses ncs_rpc_notif_with-rollback-id-params;
  }
  augment "/ncs:devices/ncs:device/ncs:rpc/tr:rpc-commit-transaction/tr:commit-transaction/tr:output" {
    uses ncs_rpc_notif_with-rollback-id-reply;
  }
}
