module tailf-netconf-extensions {
  // Generated by yanger -t ncs
  tailf:mount-id "onf-tapi-nc-2.0:onf-tapi-nc-2.0";
  tailf:ncs-device-type "netconf";

  yang-version 1.1;
  namespace "http://tail-f.com/ns/netconf/extensions";
  prefix tfnce;
  // NCS drop tailf:export

  import ietf-netconf {
    prefix nc;
  }
  import tailf-common {
    prefix tailf;
  }
  import tailf-ncs {
    prefix ncs;
  }

  organization
    "Tail-f Systems";
  description
    "This module contains Tail-f specific optional augments and RPC:s.

     Extends the 'lock' RPC with a parameter 'wait-time'.

     The RPC 'has-children' provides the means for a client to prune
     the data-model when traversing the database.

     The RPC 'get-attributes' retrieves attributes for a single data
     node in an efficient manner.

     Copyright 2015-2021 Cisco Systems, Inc.
     All rights reserved.
     Permission is hereby granted to redistribute this file without
     modification.";

  revision 2021-06-18 {
    description
      "Released as part of ConfD-7.6.

       Add commit-params grouping and trace-id as its first and only member.";
  }
  revision 2019-04-09 {
    description
      "Released as part of ConfD-7.1

       Added 'wait-time' support to the 'lock' RPC.";
  }
  revision 2015-06-16 {
    description
      "Initial revision.";
  }

  grouping ncs_template_commit-params {
    leaf trace-id {
      type string;
      description
        "Use the provided trace id as part of the log messages emitted while
         processing.

         If no trace id is given, a system generated trace id is going to be
         assigned for the processing.";
    }
  }

  grouping ncs_rpc_notif_commit-params {
    leaf trace-id {
      type string {
        length "1..64";
      }
      description
        "Use the provided trace id as part of the log messages emitted while
         processing.

         If no trace id is given, a system generated trace id is going to be
         assigned for the processing.";
    }
  }

  grouping live_ncs_commit-params {
    leaf trace-id {
      type string {
        length "1..64";
      }
      description
        "Use the provided trace id as part of the log messages emitted while
         processing.

         If no trace id is given, a system generated trace id is going to be
         assigned for the processing.";
    }
  }

  grouping commit-params {
    leaf trace-id {
      type string {
        length "1..64";
      }
      description
        "Use the provided trace id as part of the log messages emitted while
         processing.

         If no trace id is given, a system generated trace id is going to be
         assigned for the processing.";
    }
  }

  augment "/ncs:devices/ncs:device/ncs:rpc" {
    container rpc-get-attributes {
      tailf:ncs-device-type "netconf";
      tailf:display-when "not(../../ncs:module) or ../../ncs:module[ncs:name='tailf-netconf-extensions']";
      tailf:action get-attributes {
        tailf:actionpoint ncsproxy {
          tailf:internal;
        }
        description
          "Retrieves the meta-data attributes for a data node.
           The attributes are returned as XML attributes
           in the <result> leaf.";
        input {
          leaf path {
            type instance-identifier {
              require-instance false;
            }
          }
        }
        output {
          leaf result {
            type enumeration {
              enum "ok" {
                description
                  "Attribute list in meta-data of this node.";
              }
              enum "not_found" {
                description
                  "Data node not found.";
              }
            }
          }
        }
      }
    }
  }
  augment "/ncs:devices/ncs:device-group/ncs:ned-id/ncs:rpc" {
    container rpc-get-attributes {
      tailf:ncs-device-type "netconf";
      tailf:display-when "../../ncs:id = 'onf-tapi-nc-2.0:onf-tapi-nc-2.0'";
      tailf:action get-attributes {
        tailf:actionpoint ncsproxy {
          tailf:internal;
        }
        description
          "Retrieves the meta-data attributes for a data node.
           The attributes are returned as XML attributes
           in the <result> leaf.";
        input {
          leaf path {
            type instance-identifier {
              require-instance false;
            }
          }
        }
        output {
          container "device" {
            leaf "name" {
              type string;
            }
            leaf "info" {
              type string;
            }
            container "result" {
              leaf result {
                type enumeration {
                  enum "ok" {
                    description
                      "Attribute list in meta-data of this node.";
                  }
                  enum "not_found" {
                    description
                      "Data node not found.";
                  }
                }
              }
            }
          }
        }
      }
    }
  }
  augment "/ncs:devices/ncs:device/ncs:rpc" {
    container rpc-has-children {
      tailf:ncs-device-type "netconf";
      tailf:display-when "not(../../ncs:module) or ../../ncs:module[ncs:name='tailf-netconf-extensions']";
      tailf:action has-children {
        tailf:actionpoint ncsproxy {
          tailf:internal;
        }
        description
          "Used to find out whether a container or list instance is empty or
           not.  Returns false if and only if the sub-tree is guaranteed to not
           contain any configuration data, otherwise 'maybe'.";
        input {
          leaf path {
            type instance-identifier {
              require-instance false;
            }
          }
        }
        output {
          leaf result {
            type enumeration {
              enum "maybe" {
                description
                  "Data may exist below <path>.";
              }
              enum "false" {
                description
                  "No data exists below <path>.";
              }
            }
          }
        }
      }
    }
  }
  augment "/ncs:devices/ncs:device-group/ncs:ned-id/ncs:rpc" {
    container rpc-has-children {
      tailf:ncs-device-type "netconf";
      tailf:display-when "../../ncs:id = 'onf-tapi-nc-2.0:onf-tapi-nc-2.0'";
      tailf:action has-children {
        tailf:actionpoint ncsproxy {
          tailf:internal;
        }
        description
          "Used to find out whether a container or list instance is empty or
           not.  Returns false if and only if the sub-tree is guaranteed to not
           contain any configuration data, otherwise 'maybe'.";
        input {
          leaf path {
            type instance-identifier {
              require-instance false;
            }
          }
        }
        output {
          container "device" {
            leaf "name" {
              type string;
            }
            leaf "info" {
              type string;
            }
            container "result" {
              leaf result {
                type enumeration {
                  enum "maybe" {
                    description
                      "Data may exist below <path>.";
                  }
                  enum "false" {
                    description
                      "No data exists below <path>.";
                  }
                }
              }
            }
          }
        }
      }
    }
  }
  augment "/ncs:devices/ncs:device/ncs:config" {
    uses commit-params {
      refine trace-id {
        tailf:ncs-device-type "netconf";
        tailf:display-when "not(../../ncs:module) or ../../ncs:module[ncs:name='tailf-netconf-extensions']";
      }
    }
  }
  augment "/ncs:devices/ncs:device/ncs:live-status" {
    uses live_ncs_commit-params {
      refine trace-id {
        tailf:ncs-device-type "netconf";
        tailf:display-when "not(../../ncs:module) or ../../ncs:module[ncs:name='tailf-netconf-extensions'] or (../../ncs:live-status-protocol[not(ncs:capability)]) or (../../ncs:live-status-protocol/ncs:capability/ncs:module[.='tailf-netconf-extensions'])";
      }
    }
  }
  augment "/ncs:devices/ncs:template/ncs:ned-id/ncs:config" {
    uses ncs_template_commit-params;
  }
  augment "/ncs:devices/ncs:device/ncs:rpc/nc:rpc-lock/nc:lock/nc:input" {
    leaf wait-time {
      type union {
        type uint32;
        type enumeration {
          enum "infinity";
        }
      }
      units "seconds";
      description
        "If this parameter is given, and the lock is already held by
         some other session, the server waits for the specified amount
         of seconds for the lock to be released. If the lock cannot be
         granted within the specified amount of time, a 'lock-denied'
         error is returned.";
    }
  }
}
