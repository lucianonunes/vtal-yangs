module tapi-dsr {
  // Generated by yanger -t ncs
  tailf:mount-id "onf-tapi-nc-2.0:onf-tapi-nc-2.0";
  tailf:ncs-device-type "netconf";

  namespace "urn:onf:otcc:yang:tapi-dsr";
  prefix tapi-dsr;

  import tapi-common {
    prefix tapi-common;
  }
  import tailf-common {
    prefix tailf;
  }
  import tailf-ncs {
    prefix ncs;
  }

  organization
    "ONF OTCC (Open Transport Configuration & Control) Project";
  contact
    "
     Project Web: <https://urldefense.com/v3/__https://wiki.opennetworking.org/display/OTCC/TAPI__;!!OSsGDw!d_dJlNtYLmD585It0DKukzB2TS5KZqBZQ-pdI1D-6c6c5hRDotd6G39KDEbL$ >
     Project List: <mailto:transport-api@opennetworking.org>
     Editor: Karthik Sethuraman <mailto:karthik.sethuraman@necam.com>
     Andrea Mazzini <mailto:andrea.mazzini@nokia.com>
     Arturo Mayoral <mailto:arturo.mayoral@telefonica.com>
     Nigel Davis <mailto:ndavis@ciena.com>";
  description
    "
     This module contains TAPI DSR Model definitions.
     Source: TapiDsr.uml
     - The TAPI YANG models included in this TAPI release are a *normative* part of the TAPI SDK.
     - The YANG specifications have been generated from the corresponding UML model using the [ONF EAGLE UML2YANG mapping tool]
     <https://urldefense.com/v3/__https://github.com/OpenNetworkingFoundation/EagleUmlYang__;!!OSsGDw!d_dJlNtYLmD585It0DKukzB2TS5KZqBZQ-pdI1D-6c6c5hRDotd6G4QHf0bG$ >
     and further edited manually to comply with the [ONF IISOMI UML2YANG mapping guidelines]
     <https://urldefense.com/v3/__https://wiki.opennetworking.org/display/OIMT/UML*-*YANG*Guidelines__;Kysr!!OSsGDw!d_dJlNtYLmD585It0DKukzB2TS5KZqBZQ-pdI1D-6c6c5hRDotd6G8IIivez$ >
     - Status of YANG model artifacts can be determined by referring to the corresponding UML artifacts.
     As described in the UML models, some artifacts are considered *experimental*, and thus the corresponding YANG artifacts.
     - The ONF TAPI release process does not guarantee backward compatibility of YANG models across major versions of TAPI releases.
     The YANG model backward compatibility criteria are outlined in section 11 of <https://urldefense.com/v3/__https://tools.ietf.org/html/rfc7950__;!!OSsGDw!d_dJlNtYLmD585It0DKukzB2TS5KZqBZQ-pdI1D-6c6c5hRDotd6G3bKxRf2$ >.
     YANG models included in this release may not be backward compatible with previous TAPI releases.
     Copyright (c) 2018 Open Networking Foundation (ONF). All rights reserved.
     License: This module is distributed under the Apache License 2.0";

  revision 2020-04-23 {
    description
      "ONF Transport API version 2.1.3.
       Changes included in this TAPI release (v2.1.3) are listed in
       <https://urldefense.com/v3/__https://github.com/OpenNetworkingFoundation/TAPI/blob/develop_v2_1/CHANGE_LOG/change-log.2.1.3.md__;!!OSsGDw!d_dJlNtYLmD585It0DKukzB2TS5KZqBZQ-pdI1D-6c6c5hRDotd6G7tqhxFK$ >";
    reference
      "ONF-TR-527, ONF-TR-512, ONF-TR-531, RFC 7950, RFC 6087 and ONF TAPI UML model
       <https://urldefense.com/v3/__https://github.com/OpenNetworkingFoundation/TAPI/tree/v2.1.0/UML__;!!OSsGDw!d_dJlNtYLmD585It0DKukzB2TS5KZqBZQ-pdI1D-6c6c5hRDotd6G7KeAhLL$ >";
  }
  revision 2019-07-16 {
    description
      "ONF Transport API version 2.1.2.
       Changes included in this TAPI release (v2.1.2) are listed in
       <https://urldefense.com/v3/__https://github.com/OpenNetworkingFoundation/TAPI/blob/develop_v2_1/CHANGE_LOG/change-log.2.1.2.md__;!!OSsGDw!d_dJlNtYLmD585It0DKukzB2TS5KZqBZQ-pdI1D-6c6c5hRDotd6G7eDS6-t$ >";
    reference
      "ONF-TR-527, ONF-TR-512, ONF-TR-531, RFC 7950, RFC 6087 and ONF TAPI UML model
       <https://urldefense.com/v3/__https://github.com/OpenNetworkingFoundation/TAPI/tree/v2.1.0/UML__;!!OSsGDw!d_dJlNtYLmD585It0DKukzB2TS5KZqBZQ-pdI1D-6c6c5hRDotd6G7KeAhLL$ >";
  }
  revision 2018-12-10 {
    description
      "ONF Transport API version 2.1.1.
       Changes included in this TAPI release (v2.1.1) are listed in
       <https://urldefense.com/v3/__https://github.com/OpenNetworkingFoundation/TAPI/blob/develop/CHANGE_LOG/change-log.2.1.1.md__;!!OSsGDw!d_dJlNtYLmD585It0DKukzB2TS5KZqBZQ-pdI1D-6c6c5hRDotd6G1ftwU5J$ >";
    reference
      "ONF-TR-527, ONF-TR-512, ONF-TR-531, RFC 7950, RFC 6087 and ONF TAPI UML model
       <https://urldefense.com/v3/__https://github.com/OpenNetworkingFoundation/TAPI/tree/v2.1.0/UML__;!!OSsGDw!d_dJlNtYLmD585It0DKukzB2TS5KZqBZQ-pdI1D-6c6c5hRDotd6G7KeAhLL$ >";
  }
  revision 2018-10-16 {
    description
      "ONF Transport API version 2.1.0.
       Changes included in this TAPI release (v2.1.0) are listed in
       <https://urldefense.com/v3/__https://github.com/OpenNetworkingFoundation/TAPI/blob/develop/CHANGE_LOG/change-log.2.1.0.md__;!!OSsGDw!d_dJlNtYLmD585It0DKukzB2TS5KZqBZQ-pdI1D-6c6c5hRDotd6G-5JStw4$ >";
    reference
      "ONF-TR-527, ONF-TR-512, ONF-TR-531, RFC 7950, RFC 6087 and ONF TAPI UML model
       <https://urldefense.com/v3/__https://github.com/OpenNetworkingFoundation/TAPI/tree/v2.1.0/UML__;!!OSsGDw!d_dJlNtYLmD585It0DKukzB2TS5KZqBZQ-pdI1D-6c6c5hRDotd6G7KeAhLL$ >";
  }
  revision 2018-03-07 {
    description
      "ONF Transport API version 2.0.2
       This YANG module has been generated from the TAPI UML Model using the IISOMI-Eagle xmi2yang mapping tool.
       Changes in this revision: <https://urldefense.com/v3/__https://github.com/OpenNetworkingFoundation/TAPI/blob/develop/CHANGE_LOG/change-log.2.0.2.md__;!!OSsGDw!d_dJlNtYLmD585It0DKukzB2TS5KZqBZQ-pdI1D-6c6c5hRDotd6G1Yf4AAN$ >";
    reference
      "ONF-TR-527, ONF-TR-512, ONF-TR-531, RFC 6020, RFC 6087 and ONF TAPI UML model
       <https://urldefense.com/v3/__https://github.com/OpenNetworkingFoundation/TAPI/tree/v2.0.2/UML__;!!OSsGDw!d_dJlNtYLmD585It0DKukzB2TS5KZqBZQ-pdI1D-6c6c5hRDotd6G27-pJK_$ >";
  }
  revision 2018-02-16 {
    description
      "ONF Transport API version 2.0.1
       This YANG module has been generated from the TAPI UML Model using the IISOMI-Eagle xmi2yang mapping tool.
       Changes in this revision: <https://urldefense.com/v3/__https://github.com/OpenNetworkingFoundation/TAPI/blob/develop/CHANGE_LOG/change-log.2.0.1.md__;!!OSsGDw!d_dJlNtYLmD585It0DKukzB2TS5KZqBZQ-pdI1D-6c6c5hRDotd6G8RnGvXg$ >";
    reference
      "ONF-TR-527, ONF-TR-512, ONF-TR-531, RFC 6020, RFC 6087 and ONF TAPI UML model
       <https://urldefense.com/v3/__https://github.com/OpenNetworkingFoundation/TAPI/tree/v2.0.1/UML__;!!OSsGDw!d_dJlNtYLmD585It0DKukzB2TS5KZqBZQ-pdI1D-6c6c5hRDotd6Gy6YoeAv$ >";
  }
  revision 2018-01-02 {
    description
      "ONF Transport API version 2.0.0
       This YANG module has been generated from the TAPI UML Model using the IISOMI-Eagle xmi2yang mapping tool.
       Changes in this revision: <https://urldefense.com/v3/__https://github.com/OpenNetworkingFoundation/TAPI/blob/develop/CHANGE_LOG/change-log.2.0.0.md__;!!OSsGDw!d_dJlNtYLmD585It0DKukzB2TS5KZqBZQ-pdI1D-6c6c5hRDotd6GyqYDgG_$ >";
    reference
      "ONF-TR-527, ONF-TR-512, ONF-TR-531, RFC 6020, RFC 6087 and ONF TAPI UML model
       <https://urldefense.com/v3/__https://github.com/OpenNetworkingFoundation/TAPI/tree/v2.0.0/UML__;!!OSsGDw!d_dJlNtYLmD585It0DKukzB2TS5KZqBZQ-pdI1D-6c6c5hRDotd6G1V9Thk9$ >";
  }

  typedef ncs_template_digital-signal-type {
    type string;
    description
      "none";
  }

  typedef ncs_rpc_notif_digital-signal-type {
    type identityref {
      base DIGITAL_SIGNAL_TYPE;
    }
    description
      "none";
  }

  typedef live_ncs_digital-signal-type {
    type identityref {
      base DIGITAL_SIGNAL_TYPE;
    }
    description
      "none";
  }

  typedef digital-signal-type {
    type identityref {
      base DIGITAL_SIGNAL_TYPE;
    }
    description
      "none";
  }

  identity DIGITAL_SIGNAL_TYPE_SDI_3G {
    base DIGITAL_SIGNAL_TYPE;
    description
      "none";
  }

  identity DIGITAL_SIGNAL_TYPE_SDI_1G5 {
    base DIGITAL_SIGNAL_TYPE;
    description
      "none";
  }

  identity DIGITAL_SIGNAL_TYPE_SDI {
    base DIGITAL_SIGNAL_TYPE;
    description
      "none";
  }

  identity DIGITAL_SIGNAL_TYPE_DVB_ASI {
    base DIGITAL_SIGNAL_TYPE;
    description
      "none";
  }

  identity DIGITAL_SIGNAL_TYPE_SBCON_ESCON {
    base DIGITAL_SIGNAL_TYPE;
    description
      "none";
  }

  identity DIGITAL_SIGNAL_TYPE_IB_QDR {
    base DIGITAL_SIGNAL_TYPE;
    description
      "none";
  }

  identity DIGITAL_SIGNAL_TYPE_IB_DDR {
    base DIGITAL_SIGNAL_TYPE;
    description
      "none";
  }

  identity DIGITAL_SIGNAL_TYPE_IB_SDR {
    base DIGITAL_SIGNAL_TYPE;
    description
      "none";
  }

  identity DIGITAL_SIGNAL_TYPE_XGPON {
    base DIGITAL_SIGNAL_TYPE;
    description
      "none";
  }

  identity DIGITAL_SIGNAL_TYPE_GPON {
    base DIGITAL_SIGNAL_TYPE;
    description
      "none";
  }

  identity DIGITAL_SIGNAL_TYPE_OTU_4 {
    base DIGITAL_SIGNAL_TYPE;
    description
      "none";
  }

  identity DIGITAL_SIGNAL_TYPE_OTU_3 {
    base DIGITAL_SIGNAL_TYPE;
    description
      "none";
  }

  identity DIGITAL_SIGNAL_TYPE_OTU_2E {
    base DIGITAL_SIGNAL_TYPE;
    description
      "none";
  }

  identity DIGITAL_SIGNAL_TYPE_OTU_2 {
    base DIGITAL_SIGNAL_TYPE;
    description
      "none";
  }

  identity DIGITAL_SIGNAL_TYPE_OTU_1 {
    base DIGITAL_SIGNAL_TYPE;
    description
      "none";
  }

  identity DIGITAL_SIGNAL_TYPE_OC_768 {
    base DIGITAL_SIGNAL_TYPE;
    description
      "none";
  }

  identity DIGITAL_SIGNAL_TYPE_OC_192 {
    base DIGITAL_SIGNAL_TYPE;
    description
      "none";
  }

  identity DIGITAL_SIGNAL_TYPE_OC_48 {
    base DIGITAL_SIGNAL_TYPE;
    description
      "none";
  }

  identity DIGITAL_SIGNAL_TYPE_OC_12 {
    base DIGITAL_SIGNAL_TYPE;
    description
      "none";
  }

  identity DIGITAL_SIGNAL_TYPE_OC_3 {
    base DIGITAL_SIGNAL_TYPE;
    description
      "none";
  }

  identity DIGITAL_SIGNAL_TYPE_STM_256 {
    base DIGITAL_SIGNAL_TYPE;
    description
      "none";
  }

  identity DIGITAL_SIGNAL_TYPE_STM_64 {
    base DIGITAL_SIGNAL_TYPE;
    description
      "none";
  }

  identity DIGITAL_SIGNAL_TYPE_STM_16 {
    base DIGITAL_SIGNAL_TYPE;
    description
      "none";
  }

  identity DIGITAL_SIGNAL_TYPE_STM_4 {
    base DIGITAL_SIGNAL_TYPE;
    description
      "none";
  }

  identity DIGITAL_SIGNAL_TYPE_STM_1 {
    base DIGITAL_SIGNAL_TYPE;
    description
      "none";
  }

  identity DIGITAL_SIGNAL_TYPE_FC_3200 {
    base DIGITAL_SIGNAL_TYPE;
    description
      "none";
  }

  identity DIGITAL_SIGNAL_TYPE_FC_1600 {
    base DIGITAL_SIGNAL_TYPE;
    description
      "none";
  }

  identity DIGITAL_SIGNAL_TYPE_FC_1200 {
    base DIGITAL_SIGNAL_TYPE;
    description
      "none";
  }

  identity DIGITAL_SIGNAL_TYPE_FC_800 {
    base DIGITAL_SIGNAL_TYPE;
    description
      "none";
  }

  identity DIGITAL_SIGNAL_TYPE_FC_400 {
    base DIGITAL_SIGNAL_TYPE;
    description
      "none";
  }

  identity DIGITAL_SIGNAL_TYPE_FC_200 {
    base DIGITAL_SIGNAL_TYPE;
    description
      "none";
  }

  identity DIGITAL_SIGNAL_TYPE_FC_100 {
    base DIGITAL_SIGNAL_TYPE;
    description
      "none";
  }

  identity DIGITAL_SIGNAL_TYPE_100_GigE {
    base DIGITAL_SIGNAL_TYPE;
    description
      "none";
  }

  identity DIGITAL_SIGNAL_TYPE_40_GigE {
    base DIGITAL_SIGNAL_TYPE;
    description
      "none";
  }

  identity DIGITAL_SIGNAL_TYPE_10_GigE_WAN {
    base DIGITAL_SIGNAL_TYPE;
    description
      "none";
  }

  identity DIGITAL_SIGNAL_TYPE_10_GigE_LAN {
    base DIGITAL_SIGNAL_TYPE;
    description
      "none";
  }

  identity DIGITAL_SIGNAL_TYPE_GigE {
    base DIGITAL_SIGNAL_TYPE;
    description
      "none";
  }

  identity DIGITAL_SIGNAL_TYPE {
    base tapi-common:LAYER_PROTOCOL_QUALIFIER;
    description
      "none";
  }
}
