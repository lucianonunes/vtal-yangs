module ietf-netconf-partial-lock {
  // Generated by yanger -t ncs
  tailf:mount-id "onf-tapi-nc-2.0:onf-tapi-nc-2.0";
  tailf:ncs-device-type "netconf";

  namespace "urn:ietf:params:xml:ns:netconf:partial-lock:1.0";
  prefix pl;

  import tailf-common {
    prefix tailf;
  }
  import tailf-ncs {
    prefix ncs;
  }

  organization
    "IETF Network Configuration (netconf) Working Group";
  contact
    "Netconf Working Group
     Mailing list: netconf@ietf.org
     Web: http://www.ietf.org/html.charters/netconf-charter.html

     Balazs Lengyel
     Ericsson
     balazs.lengyel@ericsson.com";
  description
    "This YANG module defines the <partial-lock> and
     <partial-unlock> operations.";

  revision 2009-10-19 {
    description
      "Initial version, published as RFC 5717.";
  }

  typedef ncs_template_lock-id-type {
    type string;
    description
      "A number identifying a specific partial-lock granted to a session.
       It is allocated by the system, and SHOULD be used in the
       partial-unlock operation.";
  }

  typedef ncs_rpc_notif_lock-id-type {
    type uint32;
    description
      "A number identifying a specific partial-lock granted to a session.
       It is allocated by the system, and SHOULD be used in the
       partial-unlock operation.";
  }

  typedef live_ncs_lock-id-type {
    type uint32;
    description
      "A number identifying a specific partial-lock granted to a session.
       It is allocated by the system, and SHOULD be used in the
       partial-unlock operation.";
  }

  typedef lock-id-type {
    type uint32;
    description
      "A number identifying a specific partial-lock granted to a session.
       It is allocated by the system, and SHOULD be used in the
       partial-unlock operation.";
  }

  augment "/ncs:devices/ncs:device/ncs:rpc" {
    container rpc-partial-unlock {
      tailf:ncs-device-type "netconf";
      tailf:display-when "not(../../ncs:module) or ../../ncs:module[ncs:name='ietf-netconf-partial-lock']";
      tailf:action partial-unlock {
        tailf:actionpoint ncsproxy {
          tailf:internal;
        }
        description
          "A NETCONF operation that releases a previously acquired
           partial-lock.";
        input {
          leaf lock-id {
            type ncs_rpc_notif_lock-id-type;
            description
              "Identifies the lock to be released.  MUST be the value
               received in the response to a partial-lock operation.";
          }
        }
      }
    }
  }
  augment "/ncs:devices/ncs:device-group/ncs:ned-id/ncs:rpc" {
    container rpc-partial-unlock {
      tailf:ncs-device-type "netconf";
      tailf:display-when "../../ncs:id = 'onf-tapi-nc-2.0:onf-tapi-nc-2.0'";
      tailf:action partial-unlock {
        tailf:actionpoint ncsproxy {
          tailf:internal;
        }
        description
          "A NETCONF operation that releases a previously acquired
           partial-lock.";
        input {
          leaf lock-id {
            type ncs_rpc_notif_lock-id-type;
            description
              "Identifies the lock to be released.  MUST be the value
               received in the response to a partial-lock operation.";
          }
        }
      }
    }
  }
  augment "/ncs:devices/ncs:device/ncs:rpc" {
    container rpc-partial-lock {
      tailf:ncs-device-type "netconf";
      tailf:display-when "not(../../ncs:module) or ../../ncs:module[ncs:name='ietf-netconf-partial-lock']";
      tailf:action partial-lock {
        tailf:actionpoint ncsproxy {
          tailf:internal;
        }
        description
          "A NETCONF operation that locks parts of the running datastore.";
        input {
          leaf-list select {
            type string;
            min-elements 1;
            description
              "XPath expression that specifies the scope of the lock.
               An Instance Identifier expression MUST be used unless the
               :xpath capability is supported, in which case any XPath 1.0
               expression is allowed.";
          }
        }
        output {
          leaf lock-id {
            type ncs_rpc_notif_lock-id-type;
            description
              "Identifies the lock, if granted.  The lock-id SHOULD be
               used in the partial-unlock rpc.";
          }
          leaf-list locked-node {
            type instance-identifier;
            min-elements 1;
            description
              "List of locked nodes in the running datastore";
          }
        }
      }
    }
  }
  augment "/ncs:devices/ncs:device-group/ncs:ned-id/ncs:rpc" {
    container rpc-partial-lock {
      tailf:ncs-device-type "netconf";
      tailf:display-when "../../ncs:id = 'onf-tapi-nc-2.0:onf-tapi-nc-2.0'";
      tailf:action partial-lock {
        tailf:actionpoint ncsproxy {
          tailf:internal;
        }
        description
          "A NETCONF operation that locks parts of the running datastore.";
        input {
          leaf-list select {
            type string;
            min-elements 1;
            description
              "XPath expression that specifies the scope of the lock.
               An Instance Identifier expression MUST be used unless the
               :xpath capability is supported, in which case any XPath 1.0
               expression is allowed.";
          }
        }
        output {
          container "device" {
            leaf "name" {
              type string;
            }
            leaf "info" {
              type string;
            }
            container "result" {
              leaf lock-id {
                type ncs_rpc_notif_lock-id-type;
                description
                  "Identifies the lock, if granted.  The lock-id SHOULD be
                   used in the partial-unlock rpc.";
              }
              leaf-list locked-node {
                type instance-identifier;
                min-elements 1;
                description
                  "List of locked nodes in the running datastore";
              }
            }
          }
        }
      }
    }
  }
}
