module tailf-webui {
  // Generated by yanger -t ncs
  tailf:mount-id "onf-tapi-nc-2.0:onf-tapi-nc-2.0";
  tailf:ncs-device-type "netconf";

  namespace "http://tail-f.com/ns/webui";
  prefix webui;

  import ietf-netconf-acm {
    prefix nacm;
  }
  import tailf-common {
    prefix tailf;
  }
  import tailf-ncs {
    prefix ncs;
  }

  organization
    "Tail-f Systems";
  description
    "This module defines the Tail-f Web UI data model.

     Copyright 2013 Cisco Systems, Inc.
     All rights reserved.
     Permission is hereby granted to redistribute this file without
     modification.";

  revision 2013-03-07 {
    description
      "Initial release containing graphical panel and data storage support";
  }

  grouping ncs_template_base-key-value-store {
    leaf key {
      type string;
    }
    leaf value {
      type string;
    }
  }

  grouping ncs_template_base-saved-query-store {
    leaf list-path {
      type string;
    }
    leaf name {
      type string;
    }
    leaf serialized-query {
      type string;
      // NCS drop mandatory statement
    }
  }

  grouping ncs_rpc_notif_base-key-value-store {
    leaf key {
      type string;
      tailf:info
        "Identifies a unique entry in the store";
    }
    leaf value {
      type string;
      tailf:info
        "String based blob, for example JSON or base64 encoded string";
    }
  }

  grouping ncs_rpc_notif_base-saved-query-store {
    leaf list-path {
      type string;
      tailf:info
        "Identifies a unique list instance";
    }
    leaf name {
      type string;
      tailf:info
        "The name of the saved query";
    }
    leaf serialized-query {
      type string;
      mandatory true;
      tailf:info
        "Web UI query serialized as JSON";
    }
  }

  grouping live_ncs_base-key-value-store {
    leaf key {
      type string;
      tailf:info
        "Identifies a unique entry in the store";
    }
    leaf value {
      type string;
      tailf:info
        "String based blob, for example JSON or base64 encoded string";
    }
  }

  grouping live_ncs_base-saved-query-store {
    leaf list-path {
      type string;
      tailf:info
        "Identifies a unique list instance";
    }
    leaf name {
      type string;
      tailf:info
        "The name of the saved query";
    }
    leaf serialized-query {
      type string;
      // NCS drop mandatory statement
      tailf:info
        "Web UI query serialized as JSON";
    }
  }

  grouping base-key-value-store {
    leaf key {
      type string;
      tailf:info
        "Identifies a unique entry in the store";
    }
    leaf value {
      type string;
      tailf:info
        "String based blob, for example JSON or base64 encoded string";
    }
  }

  grouping base-saved-query-store {
    leaf list-path {
      type string;
      tailf:info
        "Identifies a unique list instance";
    }
    leaf name {
      type string;
      tailf:info
        "The name of the saved query";
    }
    leaf serialized-query {
      type string;
      mandatory true;
      tailf:info
        "Web UI query serialized as JSON";
    }
  }

  augment "/ncs:devices/ncs:device/ncs:config" {
    container webui {
      tailf:ncs-device-type "netconf";
      tailf:display-when "not(../../ncs:module) or ../../ncs:module[ncs:name='tailf-webui']";
      tailf:info
        "Web UI specific configuration";
      container schematics {
        tailf:info
          "Diagrams and reusable assets for the same";
        container panels {
          tailf:info
            "For drawing diagrams";
          list panel {
            tailf:info
              "Diagrams containing images and other components";
            key "name";
            leaf name {
              tailf:info
                "A unique name for the panel";
              type string;
            }
            container properties {
              tailf:info
                "Optional panel properties";
              leaf title {
                tailf:info
                  "The panel heading";
                type string;
              }
              leaf description {
                tailf:info
                  "What this panel is about";
                type string;
              }
              leaf width {
                tailf:info
                  "Width in pixels";
                type uint16;
              }
              leaf height {
                tailf:info
                  "Height in pixels";
                type uint16;
              }
            }
            container components {
              tailf:info
                "";
              list component {
                key "id";
                leaf id {
                  tailf:info
                    "Identifies this component uniquely.";
                  type string;
                }
                container properties {
                  leaf top {
                    tailf:info
                      "Top-to-bottom coordinate in pixels";
                    type uint16;
                  }
                  leaf left {
                    tailf:info
                      "Left-to-right coordinate in pixels";
                    type uint16;
                  }
                  leaf width {
                    tailf:info
                      "Width in pixels";
                    type uint16;
                  }
                  leaf height {
                    tailf:info
                      "Height in pixels";
                    type uint16;
                  }
                  leaf z-index {
                    tailf:info
                      "How the components are stacked on the z-axis";
                    type int16;
                  }
                  choice component-type {
                    mandatory true;
                    case image {
                      container image {
                        leaf image {
                          mandatory true;
                          tailf:info
                            "The image to display";
                          type leafref {
                            path "/ncs:devices/ncs:device/ncs:config/webui/schematics/assets/asset/name" {
                              tailf:xpath-root 3;
                            }
                          }
                        }
                      }
                    }
                    case link {
                      container link {
                        leaf text {
                          tailf:info
                            "The link text";
                          type string;
                        }
                        leaf link {
                          mandatory true;
                          tailf:info
                            "The link itself";
                          type string;
                        }
                      }
                    }
                  }
                }
              }
            }
          }
        }
        container assets {
          tailf:info
            "Sharable assets such as images and movies";
          list asset {
            key "name";
            leaf name {
              tailf:info
                "A unique name for the asset";
              type string;
            }
            choice asset-type {
              case image {
                leaf base-64-image {
                  mandatory true;
                  tailf:info
                    "Base64 encoded image";
                  type string;
                }
                leaf type {
                  mandatory true;
                  tailf:info
                    "Image file format";
                  type enumeration {
                    enum "jpeg";
                    enum "png";
                    enum "gif";
                  }
                }
              }
            }
          }
        }
      }
      container data-stores {
        tailf:info
          "Persistent data-stores used by the Web UI";
        list user-profile {
          nacm:default-deny-all;
          tailf:info
            "Stores profiles for specific users in JSON format";
          key "username";
          leaf username {
            type string;
            tailf:info
              "Who the configuration belongs to";
          }
          list profile {
            tailf:info
              "User profile settings";
            key "key";
            uses base-key-value-store;
          }
          list saved-query {
            tailf:info
              "Saved search queries";
            key "list-path name";
            uses base-saved-query-store;
          }
        }
        list data-store {
          tailf:info
            "Stores ad-hoc configuration";
          key "key";
          uses base-key-value-store;
        }
        list saved-query {
          tailf:info
            "Queries that have been saved globally";
          key "list-path name";
          uses base-saved-query-store;
        }
      }
    }
  }
  augment "/ncs:devices/ncs:device/ncs:live-status" {
    container webui {
      tailf:ncs-device-type "netconf";
      tailf:display-when "not(../../ncs:module) or ../../ncs:module[ncs:name='tailf-webui'] or (../../ncs:live-status-protocol[not(ncs:capability)]) or (../../ncs:live-status-protocol/ncs:capability/ncs:module[.='tailf-webui'])";
      tailf:info
        "Web UI specific configuration";
      container schematics {
        tailf:info
          "Diagrams and reusable assets for the same";
        container panels {
          tailf:info
            "For drawing diagrams";
          list panel {
            tailf:info
              "Diagrams containing images and other components";
            key "name";
            leaf name {
              tailf:info
                "A unique name for the panel";
              type string;
            }
            container properties {
              tailf:info
                "Optional panel properties";
              leaf title {
                tailf:info
                  "The panel heading";
                type string;
              }
              leaf description {
                tailf:info
                  "What this panel is about";
                type string;
              }
              leaf width {
                tailf:info
                  "Width in pixels";
                type uint16;
              }
              leaf height {
                tailf:info
                  "Height in pixels";
                type uint16;
              }
            }
            container components {
              tailf:info
                "";
              list component {
                key "id";
                leaf id {
                  tailf:info
                    "Identifies this component uniquely.";
                  type string;
                }
                container properties {
                  leaf top {
                    tailf:info
                      "Top-to-bottom coordinate in pixels";
                    type uint16;
                  }
                  leaf left {
                    tailf:info
                      "Left-to-right coordinate in pixels";
                    type uint16;
                  }
                  leaf width {
                    tailf:info
                      "Width in pixels";
                    type uint16;
                  }
                  leaf height {
                    tailf:info
                      "Height in pixels";
                    type uint16;
                  }
                  leaf z-index {
                    tailf:info
                      "How the components are stacked on the z-axis";
                    type int16;
                  }
                  choice component-type {
                    // NCS drop mandatory statement
                    case image {
                      container image {
                        leaf image {
                          // NCS drop mandatory statement
                          tailf:info
                            "The image to display";
                          type leafref {
                            path "/ncs:devices/ncs:device/ncs:live-status/webui/schematics/assets/asset/name" {
                              tailf:xpath-root 3;
                            }
                          }
                        }
                      }
                    }
                    case link {
                      container link {
                        leaf text {
                          tailf:info
                            "The link text";
                          type string;
                        }
                        leaf link {
                          // NCS drop mandatory statement
                          tailf:info
                            "The link itself";
                          type string;
                        }
                      }
                    }
                  }
                }
              }
            }
          }
        }
        container assets {
          tailf:info
            "Sharable assets such as images and movies";
          list asset {
            key "name";
            leaf name {
              tailf:info
                "A unique name for the asset";
              type string;
            }
            choice asset-type {
              case image {
                leaf base-64-image {
                  // NCS drop mandatory statement
                  tailf:info
                    "Base64 encoded image";
                  type string;
                }
                leaf type {
                  // NCS drop mandatory statement
                  tailf:info
                    "Image file format";
                  type enumeration {
                    enum "jpeg";
                    enum "png";
                    enum "gif";
                  }
                }
              }
            }
          }
        }
      }
      container data-stores {
        tailf:info
          "Persistent data-stores used by the Web UI";
        list user-profile {
          nacm:default-deny-all;
          tailf:info
            "Stores profiles for specific users in JSON format";
          key "username";
          leaf username {
            type string;
            tailf:info
              "Who the configuration belongs to";
          }
          list profile {
            tailf:info
              "User profile settings";
            key "key";
            uses live_ncs_base-key-value-store;
          }
          list saved-query {
            tailf:info
              "Saved search queries";
            key "list-path name";
            uses live_ncs_base-saved-query-store;
          }
        }
        list data-store {
          tailf:info
            "Stores ad-hoc configuration";
          key "key";
          uses live_ncs_base-key-value-store;
        }
        list saved-query {
          tailf:info
            "Queries that have been saved globally";
          key "list-path name";
          uses live_ncs_base-saved-query-store;
        }
      }
    }
  }
  augment "/ncs:devices/ncs:template/ncs:ned-id/ncs:config" {
    container webui {
      container schematics {
        container panels {
          list panel {
            // NCS patched for predictable order
            ordered-by user;
            key "name";
            leaf name {
              type string;
            }
            container properties {
              leaf title {
                type string;
              }
              leaf description {
                type string;
              }
              leaf width {
                type string;
              }
              leaf height {
                type string;
              }
            }
            container components {
              list component {
                // NCS patched for predictable order
                ordered-by user;
                key "id";
                leaf id {
                  type string;
                }
                container properties {
                  leaf top {
                    type string;
                  }
                  leaf left {
                    type string;
                  }
                  leaf width {
                    type string;
                  }
                  leaf height {
                    type string;
                  }
                  leaf z-index {
                    type string;
                  }
                  choice component-type {
                    // NCS drop mandatory statement
                    case image {
                      container image {
                        leaf image {
                          // NCS drop mandatory statement
                          type string;
                        }
                      }
                    }
                    case link {
                      container link {
                        leaf text {
                          type string;
                        }
                        leaf link {
                          // NCS drop mandatory statement
                          type string;
                        }
                      }
                    }
                  }
                }
              }
            }
          }
        }
        container assets {
          list asset {
            // NCS patched for predictable order
            ordered-by user;
            key "name";
            leaf name {
              type string;
            }
            choice asset-type {
              case image {
                leaf base-64-image {
                  // NCS drop mandatory statement
                  type string;
                }
                leaf type {
                  // NCS drop mandatory statement
                  type string;
                }
              }
            }
          }
        }
      }
      container data-stores {
        list user-profile {
          // NCS patched for predictable order
          ordered-by user;
          nacm:default-deny-all;
          key "username";
          leaf username {
            type string;
          }
          list profile {
            // NCS patched for predictable order
            ordered-by user;
            key "key";
            uses ncs_template_base-key-value-store;
          }
          list saved-query {
            // NCS patched for predictable order
            ordered-by user;
            key "list-path name";
            uses ncs_template_base-saved-query-store;
          }
        }
        list data-store {
          // NCS patched for predictable order
          ordered-by user;
          key "key";
          uses ncs_template_base-key-value-store;
        }
        list saved-query {
          // NCS patched for predictable order
          ordered-by user;
          key "list-path name";
          uses ncs_template_base-saved-query-store;
        }
      }
    }
  }
}
