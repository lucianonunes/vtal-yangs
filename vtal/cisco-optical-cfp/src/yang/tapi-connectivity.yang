module tapi-connectivity {
    namespace "urn:onf:otcc:yang:tapi-connectivity";
    prefix tapi-connectivity;
    import tapi-common {
        prefix tapi-common;
    }
    import tapi-topology {
        prefix tapi-topology;
    }
    import tapi-path-computation {
        prefix tapi-path-computation;
    }
    // NSO ADDITION START
    import ietf-yang-types { prefix yang; }
    import custom-template-hook { prefix ct-hook; }
    import tailf-kicker { prefix kicker; }
    import tailf-common { prefix tailf; }
    import tailf-ncs { prefix ncs; }
    // NSO ADDITION END

    organization "ONF OTCC (Open Transport Configuration & Control) Project";
    contact "
         Project Web: <https://urldefense.com/v3/__https://wiki.opennetworking.org/display/OTCC/TAPI__;!!OSsGDw!bx-l35NqfQHpJ8R_DmXfi2NX2ll5dMl9VbK5aS_m3ZShiVoz74Ur_yiFzE6g$ >
         Project List: <mailto:transport-api@opennetworking.org>
         Editor: Karthik Sethuraman <mailto:karthik.sethuraman@necam.com>
         Andrea Mazzini <mailto:andrea.mazzini@nokia.com>
         Arturo Mayoral <mailto:arturo.mayoral@telefonica.com>
         Nigel Davis <mailto:ndavis@ciena.com>";
    description "
        This module contains TAPI Connectivity Model definitions.
        Source: TapiConnectivity.uml
        - The TAPI YANG models included in this TAPI release are a *normative* part of the TAPI SDK.
        - The YANG specifications have been generated from the corresponding UML model using the [ONF EAGLE UML2YANG mapping tool]
        <https://urldefense.com/v3/__https://github.com/OpenNetworkingFoundation/EagleUmlYang__;!!OSsGDw!bx-l35NqfQHpJ8R_DmXfi2NX2ll5dMl9VbK5aS_m3ZShiVoz74Ur_6pxiNxl$ >
        and further edited manually to comply with the [ONF IISOMI UML2YANG mapping guidelines]
        <https://urldefense.com/v3/__https://wiki.opennetworking.org/display/OIMT/UML*-*YANG*Guidelines__;Kysr!!OSsGDw!bx-l35NqfQHpJ8R_DmXfi2NX2ll5dMl9VbK5aS_m3ZShiVoz74Ur_wxKUbJ_$ >
        - Status of YANG model artifacts can be determined by referring to the corresponding UML artifacts.
        As described in the UML models, some artifacts are considered *experimental*, and thus the corresponding YANG artifacts.
        - The ONF TAPI release process does not guarantee backward compatibility of YANG models across major versions of TAPI releases.
        The YANG model backward compatibility criteria are outlined in section 11 of <https://urldefense.com/v3/__https://tools.ietf.org/html/rfc7950__;!!OSsGDw!bx-l35NqfQHpJ8R_DmXfi2NX2ll5dMl9VbK5aS_m3ZShiVoz74Ur_zcAY1P4$ >.
        YANG models included in this release may not be backward compatible with previous TAPI releases.
        Copyright (c) 2018 Open Networking Foundation (ONF). All rights reserved.
        License: This module is distributed under the Apache License 2.0.";

    revision 2022-06-03 {
        description "Removed: core-fp-common reference.
                     Modified: read from dispatch-map to device tree.
                     Added: action list-sip to context -> connectivity-context.
                     Added: action validate-sips to context -> connectivity-context
                     Modified: controller-default-ned-id default value to onf-tapi-nc-2.0";
    }
    revision 2020-12-06 {
        description "Add NSO Addition/Modification";
    }
    revision 2020-06-16 {
        description "ONF Transport API version 2.1.3.
                   - Minor corrections in comments.
                   Changes included in this TAPI release (v2.1.3) are listed in
                   <https://urldefense.com/v3/__https://github.com/OpenNetworkingFoundation/TAPI/blob/develop_v2_1/CHANGE_LOG/change-log.2.1.3.md__;!!OSsGDw!bx-l35NqfQHpJ8R_DmXfi2NX2ll5dMl9VbK5aS_m3ZShiVoz74Ur_xm1nx_D$ >";
        reference "ONF-TR-527, ONF-TR-512, ONF-TR-531, RFC 7950, RFC 6087 and ONF TAPI UML model
                  <https://urldefense.com/v3/__https://github.com/OpenNetworkingFoundation/TAPI/tree/v2.1.0/UML__;!!OSsGDw!bx-l35NqfQHpJ8R_DmXfi2NX2ll5dMl9VbK5aS_m3ZShiVoz74Ur_8UH3XnH$ >";
    }
    revision 2019-07-16 {
        description "ONF Transport API version 2.1.2.
                   Changes included in this TAPI release (v2.1.2) are listed in
                   <https://urldefense.com/v3/__https://github.com/OpenNetworkingFoundation/TAPI/blob/develop_v2_1/CHANGE_LOG/change-log.2.1.2.md__;!!OSsGDw!bx-l35NqfQHpJ8R_DmXfi2NX2ll5dMl9VbK5aS_m3ZShiVoz74Ur_0xFu4bN$ >";
        reference "ONF-TR-527, ONF-TR-512, ONF-TR-531, RFC 7950, RFC 6087 and ONF TAPI UML model
                  <https://urldefense.com/v3/__https://github.com/OpenNetworkingFoundation/TAPI/tree/v2.1.0/UML__;!!OSsGDw!bx-l35NqfQHpJ8R_DmXfi2NX2ll5dMl9VbK5aS_m3ZShiVoz74Ur_8UH3XnH$ >";
    }
    revision 2018-12-10 {
        description "ONF Transport API version 2.1.1.
                   Changes included in this TAPI release (v2.1.1) are listed in
                   <https://urldefense.com/v3/__https://github.com/OpenNetworkingFoundation/TAPI/blob/develop/CHANGE_LOG/change-log.2.1.1.md__;!!OSsGDw!bx-l35NqfQHpJ8R_DmXfi2NX2ll5dMl9VbK5aS_m3ZShiVoz74Ur__2p0od1$ >";
        reference "ONF-TR-527, ONF-TR-512, ONF-TR-531, RFC 7950, RFC 6087 and ONF TAPI UML model
                  <https://urldefense.com/v3/__https://github.com/OpenNetworkingFoundation/TAPI/tree/v2.1.0/UML__;!!OSsGDw!bx-l35NqfQHpJ8R_DmXfi2NX2ll5dMl9VbK5aS_m3ZShiVoz74Ur_8UH3XnH$ >";
    }
    revision 2018-10-16 {
        description "ONF Transport API version 2.1.0.
                   Changes included in this TAPI release (v2.1.0) are listed in
                   <https://urldefense.com/v3/__https://github.com/OpenNetworkingFoundation/TAPI/blob/develop/CHANGE_LOG/change-log.2.1.0.md__;!!OSsGDw!bx-l35NqfQHpJ8R_DmXfi2NX2ll5dMl9VbK5aS_m3ZShiVoz74Ur_4DGi8ul$ >";
        reference "ONF-TR-527, ONF-TR-512, ONF-TR-531, RFC 7950, RFC 6087 and ONF TAPI UML model
                  <https://urldefense.com/v3/__https://github.com/OpenNetworkingFoundation/TAPI/tree/v2.1.0/UML__;!!OSsGDw!bx-l35NqfQHpJ8R_DmXfi2NX2ll5dMl9VbK5aS_m3ZShiVoz74Ur_8UH3XnH$ >";
    }
    revision 2018-03-07 {
        description "ONF Transport API version 2.0.2
        This YANG module has been generated from the TAPI UML Model using the IISOMI-Eagle xmi2yang mapping tool.
        Changes in this revision: <https://urldefense.com/v3/__https://github.com/OpenNetworkingFoundation/TAPI/blob/develop/CHANGE_LOG/change-log.2.0.2.md__;!!OSsGDw!bx-l35NqfQHpJ8R_DmXfi2NX2ll5dMl9VbK5aS_m3ZShiVoz74Ur_8KlxwJZ$ >";
        reference "ONF-TR-527, ONF-TR-512, ONF-TR-531, RFC 6020, RFC 6087 and ONF TAPI UML model
                  <https://urldefense.com/v3/__https://github.com/OpenNetworkingFoundation/TAPI/tree/v2.0.2/UML__;!!OSsGDw!bx-l35NqfQHpJ8R_DmXfi2NX2ll5dMl9VbK5aS_m3ZShiVoz74Ur_-hMD5Xl$ >";
    }
    revision 2018-02-16 {
        description "ONF Transport API version 2.0.1
        This YANG module has been generated from the TAPI UML Model using the IISOMI-Eagle xmi2yang mapping tool.
        Changes in this revision: <https://urldefense.com/v3/__https://github.com/OpenNetworkingFoundation/TAPI/blob/develop/CHANGE_LOG/change-log.2.0.1.md__;!!OSsGDw!bx-l35NqfQHpJ8R_DmXfi2NX2ll5dMl9VbK5aS_m3ZShiVoz74Ur__C1vuym$ >";
        reference "ONF-TR-527, ONF-TR-512, ONF-TR-531, RFC 6020, RFC 6087 and ONF TAPI UML model
                  <https://urldefense.com/v3/__https://github.com/OpenNetworkingFoundation/TAPI/tree/v2.0.1/UML__;!!OSsGDw!bx-l35NqfQHpJ8R_DmXfi2NX2ll5dMl9VbK5aS_m3ZShiVoz74Ur_5DYNwzZ$ >";
    }
    revision 2018-01-02 {
        description "ONF Transport API version 2.0.0
        This YANG module has been generated from the TAPI UML Model using the IISOMI-Eagle xmi2yang mapping tool.
        Changes in this revision: <https://urldefense.com/v3/__https://github.com/OpenNetworkingFoundation/TAPI/blob/develop/CHANGE_LOG/change-log.2.0.0.md__;!!OSsGDw!bx-l35NqfQHpJ8R_DmXfi2NX2ll5dMl9VbK5aS_m3ZShiVoz74Ur_1xZSBRA$ >";
        reference "ONF-TR-527, ONF-TR-512, ONF-TR-531, RFC 6020, RFC 6087 and ONF TAPI UML model
                  <https://urldefense.com/v3/__https://github.com/OpenNetworkingFoundation/TAPI/tree/v2.0.0/UML__;!!OSsGDw!bx-l35NqfQHpJ8R_DmXfi2NX2ll5dMl9VbK5aS_m3ZShiVoz74Ur_xt-GtqY$ >";
    }
    augment "/tapi-common:context" {
      container connectivity-context {
          uses connectivity-context;
          description "Augments the base TAPI Context with ConnectivityService information";
      }
      description "Augments the base TAPI Context with ConnectivityService information";
    }
   /* NSO MODIFICATION START *
    augment "/tapi-common:context/tapi-topology:topology-context/tapi-topology:topology/tapi-topology:node/tapi-topology:owned-node-edge-point" {
        container cep-list {
            uses cep-list;
            description "none";
        }
        description "none";
    }
   ** NSO MODIFICATION END */
   /**************************
    * definitions of references
    **************************/
    grouping connectivity-service-ref {
        leaf connectivity-service-uuid {
            type leafref {
                path '/tapi-common:context/tapi-connectivity:connectivity-context/tapi-connectivity:connectivity-service/tapi-connectivity:uuid';
            }
            description "none";
        }
        description "none";
    }
    grouping connectivity-service-end-point-ref {
        uses connectivity-service-ref;
        leaf connectivity-service-end-point-local-id {
            type leafref {
                path '/tapi-common:context/tapi-connectivity:connectivity-context/tapi-connectivity:connectivity-service/tapi-connectivity:end-point/tapi-connectivity:local-id';
            }
            description "none";
        }
        description "none";
    }
   /* NSO MODIFICATION START **
    grouping connection-end-point-ref {
        uses tapi-topology:node-edge-point-ref;
        leaf connection-end-point-uuid {
            type leafref {
                path '/tapi-common:context/tapi-topology:topology-context/tapi-topology:topology/tapi-topology:node/tapi-topology:owned-node-edge-point/tapi-connectivity:cep-list/tapi-connectivity:connection-end-point/tapi-connectivity:uuid';
            }
            description "none";
        }
        description "none";
    }
   ** NSO MODIFICATION END */
    grouping connection-ref {
        leaf connection-uuid {
            type leafref {
                path '/tapi-common:context/tapi-connectivity:connectivity-context/tapi-connectivity:connection/tapi-connectivity:uuid';
            }
            description "none";
        }
        description "none";
    }
    grouping switch-control-ref {
        uses connection-ref;
        leaf switch-control-uuid {
            type leafref {
                path '/tapi-common:context/tapi-connectivity:connectivity-context/tapi-connectivity:connection/tapi-connectivity:switch-control/tapi-connectivity:uuid';
            }
            description "none";
        }
        description "none";
    }
    grouping route-ref {
        uses connection-ref;
        leaf route-local-id {
            type leafref {
                path '/tapi-common:context/tapi-connectivity:connectivity-context/tapi-connectivity:connection/tapi-connectivity:route/tapi-connectivity:local-id';
            }
            description "none";
        }
        description "none";
    }

   /**************************
    * package object-classes
    **************************/
    grouping connection {
        /* NSO MODIFICATION START **
        list connection-end-point {
            uses connection-end-point-ref;
            key 'topology-uuid node-uuid node-edge-point-uuid connection-end-point-uuid';
            config false;
            min-elements 2;
            description "none";
        }
        list lower-connection {
            uses connection-ref;
            key 'connection-uuid';
            config false;
            description "An Connection object supports a recursive aggregation relationship such that the internal construction of an Connection can be exposed as multiple lower level Connection objects (partitioning).
                Aggregation is used as for the Node/Topology  to allow changes in hierarchy.
                Connection aggregation reflects Node/Topology aggregation.
                The FC represents a Cross-Connection in an NE. The Cross-Connection in an NE is not necessarily the lowest level of FC partitioning.";
        }
        list supported-client-link {
            uses tapi-topology:link-ref;
            key 'topology-uuid link-uuid';
            config false;
            description "none";
        }
        list route {
            key 'local-id';
            config false;
            uses route;
            description "none";
        }
        list switch-control {
            key 'uuid';
            config false;
            uses switch-control;
            description "none";
        }
        leaf direction {
            type tapi-common:forwarding-direction;
            config false;
            description "none";
        }
        leaf layer-protocol-name {
            type tapi-common:layer-protocol-name;
            config false;
            description "none";
        }
        container connection-spec-reference {
            config false;
            uses connection-spec-reference;
            description "Provides the reference to the spec that defines the connection type and cepRoles.";
        }
        ** NSO MODIFICATION END */
        uses tapi-common:resource-spec;
        uses tapi-common:operational-state-pac;
        description "The ForwardingConstruct (FC) object class models enabled potential for forwarding between two or more LTPs and like the LTP supports any transport protocol including all circuit and packet forms.
            At the lowest level of recursion, a FC represents a cross-connection within an NE.";
    }
    grouping connection-end-point {
        /* NSO MODIFICATION START **
        leaf layer-protocol-name {
            type tapi-common:layer-protocol-name;
            config false;
            description "none";
        }
        leaf layer-protocol-qualifier {
            type tapi-common:layer-protocol-qualifier;
            config false;
            description "none";
        }
        container parent-node-edge-point {
            uses tapi-topology:node-edge-point-ref;
            config false;
            description "none";
        }
        list client-node-edge-point {
            uses tapi-topology:node-edge-point-ref;
            key 'topology-uuid node-uuid node-edge-point-uuid';
            config false;
            description "none";
        }
        list aggregated-connection-end-point {
            uses connection-end-point-ref;
            key 'topology-uuid node-uuid node-edge-point-uuid connection-end-point-uuid';
            config false;
            description "none";
        }
        leaf connection-port-direction {
            type tapi-common:port-direction;
            config false;
            description "The orientation of defined flow at the EndPoint.";
        }
        leaf connection-port-role {
            type tapi-common:port-role;
            config false;
            description "Each EP of the FC has a role (e.g., working, protection, protected, symmetric, hub, spoke, leaf, root)  in the context of the FC with respect to the FC function. ";
        }
        list cep-role {
            uses cep-role;
            config false;
            description "Defines the role of the CEP in the context of the connection spec.
                There may be many cep role - connection spec combinations for a particular CEP where each corresponds to a specific connection associated with the CEP.";
        }
        ** NSO MODIFICATION END */
        uses tapi-common:resource-spec;
        uses tapi-common:operational-state-pac;
        uses tapi-common:termination-pac;
        description "The LogicalTerminationPoint (LTP) object class encapsulates the termination and adaptation functions of one or more transport layers.
            The structure of LTP supports all transport protocols including circuit and packet forms.";
    }
    grouping connectivity-constraint {
        leaf service-layer {
            type tapi-common:layer-protocol-name;
            description "none";
        }
        leaf service-type {
            type service-type;
            description "none";
        }
        leaf service-level {
            type string;
            description "An abstract value the meaning of which is mutually agreed – typically represents metrics such as - Class of service, priority, resiliency, availability";
        }
        container requested-capacity {
            uses tapi-common:capacity;
            description "none";
        }
        leaf connectivity-direction {
            type tapi-common:forwarding-direction;
            description "none";
        }
        container schedule {
            uses tapi-common:time-range;
            description "none";
        }
        container coroute-inclusion {
            uses connectivity-service-ref;
            description "none";
        }
        list diversity-exclusion {
            uses connectivity-service-ref;
            key 'connectivity-service-uuid';
            description "none";
        }
        leaf-list connection-exclusion {
            type tapi-common:uuid;
            description "none";
        }
        leaf-list connection-inclusion {
            type tapi-common:uuid;
            description "A ConnectivityService may use one or more existing Connections.
                A common traditional strategy is to set up “stranded” connectivity in the core of the network as “express channels” (this is essentially a serial compound link, but can be treated as simple connections)
                A connection inclusion capability allows for adoption of a discovered Connections.
                A ConnectivityService is requested with a connection inclusion constraint that identifies a connection (or chain of connections) that is bounded by CEPs that each belong to a NEP that references a SIP that is referenced by a CSEP of the ConnectivityService such that all CSEPs are satisfied by CEPs of the existing Connection. will allow discovered Connections with no stated intent to be associated with an intent via the ConnectivityService.";
        }
        description "none";
    }
    grouping connectivity-service {
        list end-point {
            key 'local-id';
            min-elements 2;
            uses connectivity-service-end-point;
            description "none";
        }
        /* NSO MODIFICATION START **
        list connection {
            uses connection-ref;
            key 'connection-uuid';
            config false;
            description "none";
        }
        ** NSO MODIFICATION END */
        uses tapi-common:service-spec;
        uses connectivity-constraint;
        uses tapi-path-computation:routing-constraint;
        uses tapi-path-computation:topology-constraint;
        uses resilience-constraint;
        uses tapi-common:admin-state-pac;
        description "The ForwardingConstruct (FC) object class models enabled potential for forwarding between two or more LTPs and like the LTP supports any transport protocol including all circuit and packet forms.
            At the lowest level of recursion, a FC represents a cross-connection within an NE.";
    }
    grouping connectivity-service-end-point {
        leaf layer-protocol-name {
            type tapi-common:layer-protocol-name;
            description "none";
        }
        leaf layer-protocol-qualifier {
            type tapi-common:layer-protocol-qualifier;
            description "none";
        }
        container service-interface-point {
            uses tapi-common:service-interface-point-ref;
            description "none";
        }
        /* NSO MODIFICATION START **
        list connection-end-point {
            uses connection-end-point-ref;
            key 'topology-uuid node-uuid node-edge-point-uuid connection-end-point-uuid';
            config false;
            description "none";
        }
        ** NSO MODIFICATION END */
        container capacity {
            uses tapi-common:capacity;
            description "none";
        }
        leaf direction {
            type tapi-common:port-direction;
            description "The orientation of defined flow at the EndPoint.";
        }
        leaf role {
            type tapi-common:port-role;
            description "Each EP of the FC has a role (e.g., working, protection, protected, symmetric, hub, spoke, leaf, root)  in the context of the FC with respect to the FC function. ";
        }
        leaf protection-role {
            type protection-role;
            description "To specify the protection role of this Port when create or update ConnectivityService.";
        }
        container peer-fwd-connectivity-service-end-point {
            uses connectivity-service-end-point-ref;
            description "none";
        }
        container protecting-connectivity-service-end-point {
            uses connectivity-service-end-point-ref;
            description "none";
        }
        container server-connectivity-service-end-point {
            uses connectivity-service-end-point-ref;
            description "none";
        }
        uses tapi-common:local-class;
        uses tapi-common:admin-state-pac;
        description "The association of the FC to LTPs is made via EndPoints.
            The EndPoint (EP) object class models the access to the FC function.
            The traffic forwarding between the associated EPs of the FC depends upon the type of FC and may be associated with FcSwitch object instances.
            In cases where there is resilience the EndPoint may convey the resilience role of the access to the FC.
            It can represent a protected (resilient/reliable) point or a protecting (unreliable working or protection) point.
            The EP replaces the Protection Unit of a traditional protection model.
            The ForwadingConstruct can be considered as a component and the EndPoint as a Port on that component";
    }
    grouping route {
        /* NSO MODIFICATION START **
        list connection-end-point {
            uses connection-end-point-ref;
            key 'topology-uuid node-uuid node-edge-point-uuid connection-end-point-uuid';
            config false;
            min-elements 2;
            description "none";
        }
        ** NSO MODIFICATION END */
        container resilience-route-pac {
            uses resilience-route;
            description "Provides optional resilience and state attributes to the Route.";
        }
        uses tapi-common:local-class;
        description "The Route of a Connection is modeled as a collection of Connection End Points.
            The logical order of the Connection End Points within the Route object can be inferred by the TAPI client by the knowledge of the Topology information.";
    }
    grouping connectivity-context {
        list connectivity-service {
            tailf:hidden ron;
            key 'uuid';
            uses connectivity-service;
            description "none";

            // NSO ADDITION START
            uses ncs:service-data;
            ncs:servicepoint tapi-connectivity-service-servicepoint;

            leaf controller {
                tailf:info "TAPI Controller";
                description "TAPI Controller";
                type leafref {
                    path "/ncs:devices/ncs:device/ncs:name";
                }
                mandatory true;
            }

            leaf passthrough {
                tailf:info "Pass-through payload";
                description "Pass-through payload";
                type empty;
            }

            uses ct-hook:template-hook;

            container action {
                tailf:action self-test {
                    tailf:actionpoint tapi-connectivity-service-self-test-actionpoint;
                    input {
                    }
                    output {
                        leaf status {
                            type string;
                        }
                        leaf message {
                            type string;
                        }
                    }
                }
            }
            // NSO ADDITION END
        }
        // NSO ADDITION START
        tailf:action cleanup {
            tailf:hidden ron;
            tailf:actionpoint tapi-connectivity-service-cleanup-internal;
            tailf:info "Clean up OPTICAL service configuration and operational data";
            description "Clean up OPTICAL service configuration and operational data";
            input {
                leaf service {
                    type string;
                    mandatory true;
                }
                leaf no-networking {
                    type boolean;
                    mandatory true;
                }
            }
            output {
                leaf success {
                    type boolean;
                    mandatory true;
                }
                leaf detail {
                    type string;
                }
            }
        }

        tailf:action error-recovery {
            tailf:hidden ron;
            tailf:actionpoint tapi-connectivity-service-error-recovery-internal;
            tailf:info "Action to recover a service during create/update/delete from a transient failures
                        like device connection issues once the device is reachable again.
                        For create/update failures, this action issues a sync on the device
                        & redeploys the service with reconcile option.
                        For delete failures, this action issues a sync on the device &
                        redeploys zombie services.";
            description "Action to recover a service during create/update/delete from a transient failures
                        like device connection issues once the device is reachable again.
                        For create/update failures, this action issues a sync on the device
                        & redeploys the service with reconcile option.
                        For delete failures, this action issues a sync on the device &
                        redeploys zombie services.";
            input {
                leaf service {
                    tailf:info "Service to recover";
                    description "Service to recover";
                    type string;
                    mandatory true;
                }
                leaf sync-direction {
                    tailf:info "sync device with sync-from or sync-to";
                    description "sync device with sync-from or sync-to";
                    type enumeration {
                        enum sync-from;
                        enum sync-to;
                    }
                    mandatory true;
                }
            }
            output {
                leaf success {
                    type boolean;
                    mandatory true;
                }
                leaf detail {
                    type string;
                }
            }
        }

        tailf:action fetch-sip {
            tailf:hidden ron;
            tailf:actionpoint tapi-connectivity-service-fetch-sip;
            tailf:info "Fetch SIP information for given ids";
            description "Fetch SIP information for given ids";
            input {
                leaf optical-controller {
                  tailf:info "Optical controller device";
                  description "Optical controller device";
                  type leafref {
                    path "/ncs:devices/ncs:device/ncs:name";
                  }
                  mandatory true;
                }
                leaf-list ids {
                  tailf:info "Keys for SIP lookup";
                  description "Keys for SIP lookup";
                  type string;
                }
            }
            output {
                leaf status {
                    type string;
                }
                leaf message {
                    type string;
                }
                leaf-list sips {
                    type string;
                }
            }
        }

        tailf:action list-sip {
            tailf:hidden ron;
            tailf:actionpoint tapi-connectivity-service-list-sip;
            tailf:info "List all SIP information on device in RON CFP format";
            description "List all SIP information on device in RON CFP format";
            input {
                leaf optical-controller {
                    tailf:info "Optical controller device";
                    description "Optical controller device";
                    type leafref {
                        path "/ncs:devices/ncs:device/ncs:name";
                    }
                    mandatory true;
                }
                leaf no-networking {
                    tailf:info "If set true, NSO will not sync-from the device before listing the SIPs.";
                    description "If set true, NSO will not sync-from the device before listing the SIPs.";
                    type boolean;
                    default false;
                }
            }
            output {
                leaf status {
                    type string;
                }
                leaf message {
                    type string;
                }
                list optical-service-interface {
                    leaf optical-sip {
                        type string;
                    }
                    key 'optical-sip';
                    leaf optical-add-drop {
                        type string;
                    }
                    leaf network-element {
                        type string;
                    }
                }
            }
        }

        tailf:action validate-sips {
            tailf:hidden ron;
            tailf:actionpoint tapi-connectivity-service-validate-sip;
            tailf:info "Validate SIP information on a given device";
            description "Validate SIP information on a given device";
            input {
                leaf optical-controller {
                    tailf:info "Optical controller device";
                    description "Optical controller device";
                    type leafref {
                        path "/ncs:devices/ncs:device/ncs:name";
                    }
                    mandatory true;
                }
                list optical-service-interface {
                    tailf:info "SIP information";
                    description "SIP information";

                    leaf index {
                        tailf:info "Index for the query";
                        description "Index for the query";
                        type int32 {
                            range "0..max";
                        }
                    }
                    key 'index';
                    choice optical-service-interface {
                        case add-drop {
                            leaf network-element {
                                tailf:info "Network Element the A/D port belongs to";
                                description "Network Element the A/D port belongs to";
                                type string;
                                mandatory true;
                            }
                            leaf optical-add-drop {
                                tailf:info "Add/Drop port in proper format like Rack/Shelf/Slot/Port1(or)Port1,Port2";
                                description "Add/Drop port in proper format like Rack/Shelf/Slot/Port1(or)Port1,Port2";
                                type string;
                                mandatory true;
                            }
                        }
                        case sip {
                            leaf optical-sip {
                                tailf:info "Explicit SIP";
                                description "Explicit SIP";
                                type string;
                                mandatory true;
                            }
                        }
                    }
                }
                leaf no-networking {
                    tailf:info "If set true, NSO will not sync-from the device before validating the SIPs.";
                    description "If set true, NSO will not sync-from the device before validating the SIPs.";
                    type boolean;
                    default false;
                }
            }
            output {
                leaf status {
                    type string;
                }
                leaf message {
                    type string;
                }
                list optical-service-interface {
                    leaf index {
                        type int32;
                    }
                    key 'index';
                    choice optical-service-interface {
                        case add-drop {
                            leaf network-element {
                                type string;
                                mandatory true;
                            }
                            leaf optical-add-drop {
                                type string;
                                mandatory true;
                            }
                        }
                        case sip {
                            leaf optical-sip {
                                type string;
                                mandatory true;
                            }
                        }
                    }
                    leaf valid {
                        type boolean;
                    }
                }
            }
        }

        tailf:action handle-netconf-notifications {
          tailf:actionpoint cisco-optical-cs-netconf-notifications;
          tailf:hidden full;
          input {
            //in future this should be uses kicker:action-input-params;
            uses kicker:action-input-params;
            //leaf uuid {
              //type string;
              //mandatory true;
            //}
          }
          output {
          }
        }

        tailf:action redeploy-kicker-callback {
          tailf:info "Custom action that is used for univeral plan kicker";
          tailf:actionpoint cisco-optical-cs-redeploy-kicker-callback;
          tailf:hidden full;
          input {
            uses kicker:action-input-params;
          }
          output {
          // No-op
          }
        }

        list connectivity-service-plan {
            tailf:info "Connectivity Service Plan";
            description "Connectivity Service Plan";
            config false;
            tailf:cdb-oper {
                tailf:persistent true;
            }
            key "uuid";

            leaf uuid {
                type string;
            }

            uses ncs:nano-plan-data;
            uses ncs:nano-plan-history;
        }

        tailf:action netconf-subscription {
            tailf:actionpoint tapi-connectivity-service-netconf-subscription-action;
            tailf:info "Subscribe to netconf notifications on an ONC.";
            description "Subscribe to netconf notifications on an ONC.";
            input {
                leaf onc {
                  tailf:info "Optical controller device";
                  description "Optical controller device";
                  type leafref {
                    path "/ncs:devices/ncs:device/ncs:name";
                  }
                  mandatory true;
                }
                leaf reconnect-interval {
                  tailf:info "Interval for re-establishing the subscription";
                  type uint32;
                  units "seconds";
                }
                leaf unsubscribe {
                  tailf:info "To unsubscribe netconf notifications on the device.";
                  type empty;
                }
            }
            output {
                leaf success {
                    type boolean;
                    mandatory true;
                }
                leaf detail {
                    type string;
                }
            }
        }

        container settings {
          tailf:hidden ron;
          tailf:info "Connectivity-context settings.";
          list netconf-subscription {
            tailf:info "Subscribe to netconf notifications on an ONC.";
            uses ncs:service-data;
            ncs:servicepoint "cisco-optical-cfp-onc-notification";
            key onc;
            leaf onc {
              type leafref {
                path "/ncs:devices/ncs:device/ncs:name";
              }
            }

            leaf reconnect-interval {
              tailf:info "Interval for re-establishing the subscription";
              type uint32;
              units "seconds";
              default 60;
            }
          }
        }
        // NSO ADDITION END

        /* NSO MODIFICATION START **
        list connection {
            key 'uuid';
            config false;
            uses connection;
            description "none";
        }
        ** NSO MODIFICATION END */
        description "none";
    }
    grouping switch {
        /* NSO MODIFICATION START **
        list selected-connection-end-point {
            uses connection-end-point-ref;
            key 'topology-uuid node-uuid node-edge-point-uuid connection-end-point-uuid';
            config false;
            min-elements 1;
            description "none";
        }
        ** NSO MODIFICATION END */
        list selected-route {
            uses route-ref;
            key 'connection-uuid route-local-id';
            config false;
            min-elements 1;
            description "none";
        }
        leaf selection-control {
            type selection-control;
            description "Degree of administrative control applied to the switch selection.";
        }
        /* NSO MODIFICATION START **
        leaf selection-reason {
            type selection-reason;
            config false;
            description "The reason for the current switch selection.";
        }
        ** NSO MODIFICATION END */
        leaf switch-direction {
            type tapi-common:port-direction;
            description "Indicates whether the switch selects from ingress to the FC or to egress of the FC, or both.";
        }
        uses tapi-common:local-class;
        description "The class models the switched forwarding of traffic (traffic flow) between FcPorts (ConnectionEndPoints) and is present where there is protection functionality in the FC (Connection).
            If an FC exposes protection (having two or more FcPorts that provide alternative identical inputs/outputs), the FC will have one or more associated FcSwitch objects to represent the alternative flow choices visible at the edge of the FC.
            The FC switch represents and defines a protection switch structure encapsulated in the FC.
            Essentially performs one of the functions of the Protection Group in a traditional model. It associates to 2 or more FcPorts each playing the role of a Protection Unit.
            One or more protection, i.e. standby/backup, FcPorts provide protection for one or more working (i.e. regular/main/preferred) FcPorts where either protection or working can feed one or more protected FcPort.
            The switch may be used in revertive or non-revertive (symmetric) mode. When in revertive mode it may define a waitToRestore time.
            It may be used in one of several modes including source switch, destination switched, source and destination switched etc (covering cases such as 1+1 and 1:1).
            It may be locked out (prevented from switching), force switched or manual switched.
            It will indicate switch state and change of state.
            The switch can be switched away from all sources such that it becomes open and hence two coordinated switches can both feed the same LTP so long as at least one of the two is switched away from all sources (is 'open').
            The ability for a Switch to be 'high impedance' allows bidirectional ForwardingConstructs to be overlaid on the same bidirectional LTP where the appropriate control is enabled to prevent signal conflict.
            This ability allows multiple alternate routes to be present that otherwise would be in conflict.";
    }
    grouping switch-control {
        /* NSO MODIFICATION START **
        list sub-switch-control {
            uses switch-control-ref;
            key 'connection-uuid switch-control-uuid';
            config false;
            description "none";
        }
        ** NSO MODIFICATION END */
        list switch {
            key 'local-id';
            uses switch;
            description "none";
        }
        uses tapi-common:resource-spec;
        uses resilience-constraint;
        description "Represents the capability to control and coordinate switches, to add/delete/modify FCs and to add/delete/modify LTPs/LPs so as to realize a protection scheme.";
    }
    grouping resilience-constraint {
        container resilience-type {
            uses tapi-topology:resilience-type;
            description "none";
        }
        leaf restoration-coordinate-type {
            type coordinate-type;
            description " The coordination mechanism between multi-layers.";
        }
        leaf restore-priority {
            type uint64;
            description "none";
        }
        leaf reversion-mode {
            type reversion-mode;
            description "Indcates whether the protection scheme is revertive or non-revertive.";
        }
        leaf wait-to-revert-time {
            type uint64;
            default "15";
            description "If the protection system is revertive, this attribute specifies the time, in minutes, to wait after a fault clears on a higher priority (preferred) resource before reverting to the preferred resource.";
        }
        leaf hold-off-time {
            type uint64;
            description "This attribute indicates the time, in milliseconds, between declaration of signal degrade or signal fail, and the initialization of the protection switching algorithm.";
        }
        leaf is-lock-out {
            type boolean;
            description "The resource is configured to temporarily not be available for use in the protection scheme(s) it is part of.
                This overrides all other protection control states including forced.
                If the item is locked out then it cannot be used under any circumstances.
                Note: Only relevant when part of a protection scheme.";
        }
        leaf is-frozen {
            type boolean;
            description "Temporarily prevents any switch action to be taken and, as such, freezes the current state.
                Until the freeze is cleared, additional near-end external commands are rejected and fault condition changes and received APS messages are ignored.
                All administrative controls of any aspect of protection are rejected.";
        }
        leaf is-coordinated-switching-both-ends {
            type boolean;
            description "Is operating such that switching at both ends of each flow acorss the FC is coordinated at both ingress and egress ends.";
        }
        leaf max-switch-times {
            type uint64;
            description "Used to limit the maximum swtich times. When work fault disappears , and traffic return to the original work path, switch counter reset.";
        }
        leaf-list preferred-restoration-layer {
            type tapi-common:layer-protocol-name;
            description "Indicate which layer this resilience parameters package configured for.";
        }
        description "A list of control parameters to apply to a switch.";
    }
    grouping cep-list {
        list connection-end-point {
            key 'uuid';
            uses connection-end-point;
            description "none";
        }
        description "none";
    }
    grouping resilience-route {
        /* NSO MODIFICATION START **
        leaf priority {
            type uint64;
            config false;
            description "Value of 0 (zero) means 'unspecified priority'.
                Highest priority is 1, sometimes referred as 'preferred' or 'main' or 'intended' route.
                2 has lower priority than 1, 3 has lower priority than 2, etc.";
        }
        leaf route-state {
            type route-state;
            config false;
            description "Current information on the route selection.";
        }
        ** NSO MODIFICATION END */
        uses tapi-common:local-class;
        description "This object adds resilience and state attributes to the Route.
            When this object is not present, then the Route is intendend as 'current' Route of the Connection.";
    }

    /**************************
    * package type-definitions
    **************************/
    identity ROUTE_STATE {
        description "none";
    }
    identity ROUTE_STATE_CURRENT {
        base ROUTE_STATE;
        description "The route identified is the current route, i.e., is the one that is active and selected to support service.
            ";
    }
    identity ROUTE_STATE_NOT_CURRENT {
        base ROUTE_STATE;
        description "The route is not the one supporting the service.";
    }
    identity ROUTE_STATE_UNKNOWN {
        base ROUTE_STATE;
        description "The route state is unknown.";
    }
    typedef service-type {
        type enumeration {
            enum POINT_TO_POINT_CONNECTIVITY {
                description "none";
            }
            enum POINT_TO_MULTIPOINT_CONNECTIVITY {
                description "none";
            }
            enum MULTIPOINT_CONNECTIVITY {
                description "none";
            }
            enum ROOTED_MULTIPOINT_CONNECTIVITY {
                description "none";
            }
        }
        description "none";
    }
    typedef reversion-mode {
        type enumeration {
            enum REVERTIVE {
                description "An FC switched to a lower priority (non-preferred) resource will revert to a higher priority (preferred) resource when that recovers (potentially after some hold-off time).";
            }
            enum NON-REVERTIVE {
                description "An FC switched to a lower priority (non-preferred) resource will not revert to a higher priority (preferred) resource when that recovers.";
            }
        }
        description "The reversion mode associated with protection.";
    }
    typedef selection-control {
        type enumeration {
            enum LOCK_OUT {
                description "The resource is configured to temporarily not be available for use in the protection scheme(s) it is part of.
                    This overrides all other protection control states including forced.
                    If the item is locked out then it cannot be used under any circumstances.
                    Note: Only relevant when part of a protection scheme.";
            }
            enum NORMAL {
                description "none";
            }
            enum MANUAL {
                description "none";
            }
            enum FORCED {
                description "none";
            }
        }
        description "Possible degrees of administrative control applied to the Route selection.";
    }
    typedef selection-reason {
        type enumeration {
            enum LOCKOUT {
                description "none";
            }
            enum NORMAL {
                description "none";
            }
            enum MANUAL {
                description "none";
            }
            enum FORCED {
                description "none";
            }
            enum WAIT_TO_REVERT {
                description "none";
            }
            enum SIGNAL_DEGRADE {
                description "none";
            }
            enum SIGNAL_FAIL {
                description "none";
            }
        }
        description "The cause of the current route selection.";
    }
    typedef coordinate-type {
        type enumeration {
            enum NO_COORDINATE {
                description "none";
            }
            enum HOLD_OFF_TIME {
                description "none";
            }
            enum WAIT_FOR_NOTIFICATION {
                description "none";
            }
        }
        description "none";
    }
    typedef protection-role {
        type enumeration {
            enum WORK {
                description "none";
            }
            enum PROTECT {
                description "none";
            }
            enum PROTECTED {
                description "none";
            }
            enum NA {
                description "none";
            }
            enum WORK_RESTORE {
                description "none";
            }
            enum PROTECT_RESTORE {
                description "none";
            }
        }
        description "none";
    }
    grouping cep-role {
        leaf role-name {
            type string;
            description "The name of the cep role in the context of the referenced spec.";
        }
        /* NSO MODIFICATION START **
        container connection-spec-reference {
            config false;
            uses connection-spec-reference;
            description "The reference to the spec that defines the cep role.";
        }
        ** NSO MODIFICATION END */
        description "The role of the cep in the context of the connection spec.";
    }
    grouping connection-spec-reference {
        /* NSO MODIFICATION START **
        leaf connection-spec-id {
            type tapi-common:uuid;
            config false;
            description "The reference to a formal spec.
                This reference need not be provided (e.g., where there is no formal machine interpretable spec for the type of connection).";
        }
        leaf connection-spec-name {
            type string;
            config false;
            description "The name of the connection spec.
                This can be used alone (with no spec reference) where there is only a paper spec.";
        }
        ** NSO MODIFICATION END */
        description "The reference to a spec for a type of connection.";
    }
    typedef route-state {
        type identityref {
            base ROUTE_STATE;
        }
        description "Potential route states.";
    }

    /**************************
    * package interfaces
    **************************/
    /* NSO MODIFICATION START **
    rpc get-connection-details {
        description "none";
        input {
            leaf connection-id-or-name {
                type string;
                description "none";
            }
        }
        output {
            container connection {
                uses connection;
                description "none";
            }
        }
    }
    rpc get-connectivity-service-list {
        description "none";
        output {
            list service {
                key 'uuid';
                uses connectivity-service;
                description "none";
            }
        }
    }
    rpc get-connectivity-service-details {
        description "none";
        input {
            leaf service-id-or-name {
                type string;
                description "none";
            }
        }
        output {
            container service {
                uses connectivity-service;
                description "none";
            }
        }
    }
    rpc create-connectivity-service {
        description "none";
        input {
            list end-point {
                key 'local-id';
                min-elements 2;
                uses connectivity-service-end-point;
                description "none";
            }
            container connectivity-constraint {
                uses connectivity-constraint;
                description "none";
            }
            container routing-constraint {
                uses tapi-path-computation:routing-constraint;
                description "none";
            }
            container topology-constraint {
                uses tapi-path-computation:topology-constraint;
                description "none";
            }
            container resilience-constraint {
                uses resilience-constraint;
                description "none";
            }
            leaf state {
                type string;
                description "none";
            }
        }
        output {
            container service {
                uses connectivity-service;
                description "none";
            }
        }
    }
    rpc update-connectivity-service {
        description "none";
        input {
            leaf service-id-or-name {
                type string;
                description "none";
            }
            list end-point {
                key 'local-id';
                uses connectivity-service-end-point;
                description "none";
            }
            container connectivity-constraint {
                uses connectivity-constraint;
                description "none";
            }
            container routing-constraint {
                uses tapi-path-computation:routing-constraint;
                description "none";
            }
            container topology-constraint {
                uses tapi-path-computation:topology-constraint;
                description "none";
            }
            container resilience-constraint {
                uses resilience-constraint;
                description "none";
            }
            leaf state {
                type string;
                description "none";
            }
        }
        output {
            container service {
                uses connectivity-service;
                description "none";
            }
        }
    }
    rpc delete-connectivity-service {
        description "none";
        input {
            leaf service-id-or-name {
                type string;
                description "none";
            }
        }
    }
    rpc get-connection-end-point-details {
        description "none";
        input {
            leaf topology-id-or-name {
                type string;
                description "none";
            }
            leaf node-id-or-name {
                type string;
                description "none";
            }
            leaf nep-id-or-name {
                type string;
                description "none";
            }
            leaf cep-id-or-name {
                type string;
                description "none";
            }
        }
        output {
            container connection-end-point {
                uses connection-end-point;
                description "none";
            }
        }
    }
    ** NSO MODIFICATION END */

    // NSO ADDITION START
    grouping connectivity-service-oper-purge-action {
      tailf:action purge {
        tailf:actionpoint cisco-optical-cs-oper-data-purge;
        tailf:info "Clean stale connectivity-service-oper-data entry";
        description
          "Calling this action will clean stale
              connectivity-service-oper-data entry.";
        output {
          leaf result {
            type string;
          }
        }
      }
    }
    grouping connectivity-service-oper-data-grouping {
      list connectivity-service-oper-data {
        config false;
        tailf:cdb-oper  {
          tailf:persistent true;
        }

        key 'uuid';
        leaf uuid {
          type string;
        }

        list lifecycle-state {
          ordered-by user;
          key "state time";
          leaf state {
            type tapi-common:lifecycle-state;
          }
          leaf time {
            type yang:date-and-time;
            mandatory true;
          }
          leaf error {
            type string;
          }
          leaf code {
            type string;
          }
        }

        list end-point {
          key 'local-id';
          leaf local-id {
            type string;
          }

          container optics-data {
            leaf transmit-power {
              type decimal64 {
                  fraction-digits 7;
              }
              tailf:info "The total power at any point in a channel specified in dBm.";
              description "The total power at any point in a channel specified in dBm.";
            }

            leaf grid-type {
              tailf:info "DWDM Channel Grid Type";
              description "DWDM Channel Grid Type";
              type enumeration {
                enum "100mhz-grid";
              }
              default "100mhz-grid";
            }

            leaf frequency {
              tailf:info "Frequency in 100MHz, C Band: 1911500-1961000,L band: 1861000-1908500";
              description "Frequency in 100MHz, C Band: 1911500-1961000,L band: 1861000-1908500";
              type uint32 {
                range "1861000..1961000";
              }
            }
          }
          uses connectivity-service-oper-purge-action;
        }
        uses connectivity-service-oper-purge-action;
      }
    }

    grouping status-code-plan-augmentation {
        list status-code-detail {
            tailf:info "Status Codes";
            description "Status Codes";
            key "type name";
            leaf type {
                type ncs:plan-component-type-t;
            }
            leaf name {
                type string;
            }
            leaf code {
                type string;
            }
            list context {
                key context-name;
                leaf context-name {
                    type string;
                }
                leaf context-msg {
                    type string;
                }
            }
            leaf severity {
                type enumeration {
                    enum INFO;
                    enum WARNING;
                    enum ERROR;
                    enum FATAL;
                    enum NONE;
                }
            }
            leaf recommended-action {
                tailf:info "Recommended action to recover in case of error";
                description "Recommended action to recover in case of error";
                type string;
            }
        }
    }

    grouping status-code-component-augmentation {
        leaf status-code {
            type string;
        }
    }

    augment /tapi-common:context/connectivity-context/connectivity-service-plan/plan {
        uses status-code-plan-augmentation;
    }

    augment /tapi-common:context/connectivity-context/connectivity-service-plan/plan-history {
        uses status-code-plan-augmentation;
    }

    augment /tapi-common:context/connectivity-context/connectivity-service-plan/plan/component {
        uses status-code-component-augmentation;
    }

    augment /tapi-common:context/connectivity-context/connectivity-service-plan/plan-history/plan/component {
        uses status-code-component-augmentation;
    }

    container cfp-configurations {
        list dynamic-device-mapping {
            tailf:info "Dynamic Device Mapping";
            description "Dynamic Device Mapping";

            tailf:validate "tapi-dynamic-map-validation" {
                tailf:dependency ".";
            }

            key "ned-id vendor";
            leaf ned-id {
                tailf:info "Device NED ID, eg ned:netconf";
                description "Device NED ID, eg ned:netconf";
                type string;
                tailf:cli-allow-range;
            }
            leaf python-impl-class-name {
                tailf:info "Device Python implementation class, eg module.class";
                description "Device Python implementation class, eg module.class";
                type string;
                mandatory true;
            }
            leaf vendor {
              tailf:info "Vendor. example CISCO";
              description "Vendor. example CISCO";
              type string;
            }
        }

        leaf controller-default-ned-id {
            tailf:info "NED ID of the default Optical Controller Device.";
            description "NED ID of the default Optical Controller Device.";
            tailf:hidden ron;
            type string;
            default "onf-tapi-nc-2.0:onf-tapi-nc-2.0";
        }

        leaf controller-default-vendor {
            tailf:info "Vendor.";
            description "Vendor.";
            tailf:hidden ron;
            type string;
            default "Cisco";
        }
    }

    augment "/tapi-common:context/tapi-connectivity:connectivity-context" {
        uses connectivity-service-oper-data-grouping;
    }
    // NSO ADDITION END
}
