module ietf-te-types {
  yang-version 1.1;
  namespace "urn:ietf:params:xml:ns:yang:ietf-te-types";

  /* Replace with IANA when assigned */
  prefix "te-types";
  
  import lsa-utils {
	prefix lsa-utils;
  }

  import ietf-inet-types {
    prefix inet;
    reference "RFC6991: Common YANG Data Types";
  }

  import ietf-yang-types {
    prefix "yang";
    reference "RFC6991: Common YANG Data Types";
  }

  import ietf-routing-types {
    prefix "rt-types";
    reference "RFC8294: Common YANG Data Types for the Routing Area";
  }

  // NSO ADDITION - START
  import tailf-common { prefix tailf; }
  import tailf-ncs { prefix ncs; }
  // NSO ADDITION - END

  organization
    "IETF Traffic Engineering Architecture and Signaling (TEAS)
     Working Group";

  contact
    "WG Web:   <http://tools.ietf.org/wg/teas/>
     WG List:  <mailto:teas@ietf.org>

     WG Chair: Lou Berger
               <mailto:lberger@labn.net>

     WG Chair: Vishnu Pavan Beeram
               <mailto:vbeeram@juniper.net>

     Editor:   Tarek Saad
               <mailto:tsaad@juniper.net>

     Editor:   Rakesh Gandhi
               <mailto:rgandhi@cisco.com>

     Editor:   Vishnu Pavan Beeram
               <mailto:vbeeram@juniper.net>

     Editor:   Himanshu Shah
               <mailto:hshah@ciena.com>

     Editor:   Xufeng Liu
               <mailto:xufeng.liu.ietf@gmail.com>

     Editor:   Igor Bryskin
               <mailto:Igor.Bryskin@huawei.com>

     Editor:   Young Lee
               <mailto:leeyoung@huawei.com>";

  description
    "This module contains a collection of generally useful TE
     specific YANG data type definitions. The model fully conforms
     to the Network Management Datastore Architecture (NMDA).

     Copyright (c) 2018 IETF Trust and the persons
     identified as authors of the code.  All rights reserved.

     Redistribution and use in source and binary forms, with or
     without modification, is permitted pursuant to, and subject
     to the license terms contained in, the Simplified BSD License
     set forth in Section 4.c of the IETF Trust's Legal Provisions
     Relating to IETF Documents
     (https://trustee.ietf.org/license-info).
     This version of this YANG module is part of RFC XXXX; see
     the RFC itself for full legal notices.";

  // RFC Ed.: replace XXXX with actual RFC number and remove this
  // note.

  // RFC Ed.: update the date below with the date of RFC publication
  // and remove this note.

  revision 2021-12-03 {
	description
	  "Removed: core-fp-common reference
	   Modified: Read dispatch-map using lsa-utils";
  }

  revision "2021-07-22" {
    description "Changed tail:info and description of leaf index under route-object-include-exclude
                 to reflect correct range";
  }

  revision "2021-05-24" {
    description "Commented out identityref for protection-external-commands and tunnel-action-type";
  }

  revision "2021-03-19" {
    description "Added must condition to restrict metric type delay-average and delay-minimum
                for XE device under optimization-metric";
  }

  revision "2021-02-15" {
    description "Removed: Unused groupings;";
  }

  revision "2021-02-04" {
    description "Added tailf:info for IETF config and updated ranges and description to support tooltip in UI";
  }

  revision "2020-12-01" {
    description "Added tailf:hidden full to hold-priority and setup-priority for p2p-path";
  }

  revision "2020-10-09" {
    description "Removed tailf:hidden full from hold-priority and setup-priority";
  }

  revision "2019-07-05" {
    description "Latest revision of TE types";
    reference
      "RFC XXXX: A YANG Data Model for Common Traffic Engineering
       Types";
  }

  /**
   * Typedefs
   */
  typedef admin-group {
    type yang:hex-string {
      /* 01:02:03:04 */
      length "1..11";
    }
    description
      "Administrative group/Resource class/Color representation in
       hex-string type.";
    reference "RFC3630 and RFC5305";
  }

  typedef admin-groups {
    type union {
      type admin-group;
      type extended-admin-group;
    }
    description "TE administrative group derived type";
  }

  typedef extended-admin-group {
    type yang:hex-string;
    description
      "Extended administrative group/Resource class/Color
       representation in hex-string type";
    reference "RFC7308";
  }

  typedef path-attribute-flags {
    type union {
      type identityref {
        base session-attributes-flags;
      }
      type identityref {
        base lsp-attributes-flags;
      }
    }
    description "Path attributes flags type";
  }

  typedef performance-metrics-normality {
    type enumeration {
      enum "unknown" {
        value 0;
        description
          "Unknown.";
      }
      enum "normal" {
        value 1;
        description
          "Normal.";
      }
      enum "abnormal" {
        value 2;
        description
          "Abnormal. The anomalous bit is set.";
      }
    }
    description
      "Indicates whether a performance metric is normal, abnormal, or
       unknown.";
    reference
      "RFC7471: OSPF Traffic Engineering (TE) Metric Extensions.
       RFC8570: IS-IS Traffic Engineering (TE) Metric Extensions.
       RFC7823: Performance-Based Path Selection for Explicitly
       Routed Label Switched Paths (LSPs) Using TE Metric
       Extensions";
  }

  typedef srlg {
    type uint32;
    description "SRLG type";
    reference "RFC4203 and RFC5307";
  }

  typedef te-admin-status {
    type enumeration {
      enum up {
        description
          "Enabled.";
      }
      enum down {
        description
          "Disabled.";
      }
      enum testing {
        description
          "In some test mode.";
      }
      enum preparing-maintenance {
        description
          "Resource is disabled in the control plane to prepare for
           graceful shutdown for maintenance purposes.";
        reference
          "RFC5817: Graceful Shutdown in MPLS and Generalized MPLS
           Traffic Engineering Networks";
      }
      enum maintenance {
        description
          "Resource is disabled in the data plane for maintenance
           purposes.";
      }
      enum unknown {
        description
          "Status is unknown";
      }
    }
    description
      "Defines a type representing the administrative status of
       a TE resource.";
  }

  typedef te-bandwidth {
    type string {
      pattern
        '0[xX](0((\.0?)?[pP](\+)?0?|(\.0?))|'
      + '1(\.([\da-fA-F]{0,5}[02468aAcCeE]?)?)?[pP](\+)?(12[0-7]|'
      + '1[01]\d|0?\d?\d)?)|0[xX][\da-fA-F]{1,8}|\d+'
      + '(,(0[xX](0((\.0?)?[pP](\+)?0?|(\.0?))|'
      + '1(\.([\da-fA-F]{0,5}[02468aAcCeE]?)?)?[pP](\+)?(12[0-7]|'
      + '1[01]\d|0?\d?\d)?)|0[xX][\da-fA-F]{1,8}|\d+))*';
    }
    tailf:info
      "Generic bandwidth Range <0-4294967295>;;Bandwidth requirement in kbps";
    description
      "This is the generic bandwidth type that is a string containing
       a list of numbers separated by commas, with each of these
       number can be non-negative decimal, hex integer, or hex float:
       (dec | hex | float)[*(','(dec | hex | float))]
       For packet switching type, a float number is used, such as
       0x1p10.
       For OTN switching type, a list of integers can be used, such
       as '0,2,3,1', indicating 2 odu0's and 1 odu3.
       For DWDM, a list of pairs of slot number and width can be
       used, such as '0, 2, 3, 3', indicating a frequency slot 0 with
       slot width 2 and a frequency slot 3 with slot width 3.
       Canonically, the string is represented as all lowercase and in
       hex where the prefix '0x' precedes the hex number";
  } // te-bandwidth

  typedef te-ds-class {
    type uint8 {
      range "0..7";
    }
    description
      "The Differentiated Class-Type of traffic.";
    reference "RFC4124: section-4.3.1";
  }

  typedef te-global-id {
    type uint32;
    description
      "An identifier to uniquely identify an operator, which can be
       either a provider or a client.
       The definition of this type is taken from RFC6370 and RFC5003.
       This attribute type is used solely to provide a globally
       unique context for TE topologies.";
  }

  typedef te-hop-type {
    type enumeration {
      enum loose {
        description
          "loose hop in an explicit path";
      }
      enum strict {
        description
          "strict hop in an explicit path";
      }
    }
    description
     "enumerated type for specifying loose or strict
      paths";
    reference "RFC3209: section-4.3.2";
  }

  typedef te-link-access-type {
    type enumeration {
      enum point-to-point {
        description
          "The link is point-to-point.";
      }
      enum multi-access {
        description
          "The link is multi-access, including broadcast and NBMA.";
      }
    }
    description
      "Defines a type representing the access type of a TE link.";
    reference
      "RFC3630: Traffic Engineering (TE) Extensions to OSPF
       Version 2.";
  }

  typedef te-label-direction {
    type enumeration {
      enum forward {
        description
          "Label allocated for the forward LSP direction";
      }
      enum reverse {
        description
          "Label allocated for the reverse LSP direction";
      }
    }
    description
     "enumerated type for specifying the forward or reverse
     label";
  }

  typedef te-link-direction {
    type enumeration {
      enum incoming {
        description
          "explicit route represents an incoming link on a node";
      }
      enum outgoing {
        description
          "explicit route represents an outgoing link on a node";
      }
    }
    description
     "enumerated type for specifying direction of link on a node";
  }

  typedef te-metric {
    type uint32;
    description "TE link metric";
    reference "RFC3785";
  }

  typedef te-node-id {
    type yang:dotted-quad;
    description
      "A type representing the identifier for a node in a TE
       topology.
       The identifier is represented as 32-bit unsigned integer in
       the dotted-quad notation.
       This attribute MAY be mapped to the Router Address described
       in Section 2.4.1 of [RFC3630], the TE Router ID described in
       Section 3 of [RFC6827], the Traffic Engineering Router ID
       described in Section 4.3 of [RFC5305], or the TE Router ID
       described in Section 3.2.1 of [RFC6119].
       The reachability of such a TE node MAY be achieved by a
       mechanism such as Section 6.2 of [RFC6827].";
  }

  typedef te-oper-status {
    type enumeration {
      enum up {
        description
        "Operational up.";
      }
      enum down {
        description
        "Operational down.";
      }
      enum testing {
        description
        "In some test mode.";
      }
      enum unknown {
        description
        "Status cannot be determined for some reason.";
      }
      enum preparing-maintenance {
        description
          "Resource is disabled in the control plane to prepare for
           graceful shutdown for maintenance purposes.";
        reference
          "RFC5817: Graceful Shutdown in MPLS and Generalized MPLS
           Traffic Engineering Networks";
      }
      enum maintenance {
        description
          "Resource is disabled in the data plane for maintenance
           purposes.";
      }
    }
    description
      "Defines a type representing the operational status of
       a TE resource.";
  }

  typedef te-path-disjointness {
    type bits {
      bit node {
        position 0;
        description "Node disjoint.";
      }
      bit link {
        position 1;
        description "Link disjoint.";
      }
      bit srlg {
        position 2;
        description "SRLG (Shared Risk Link Group) disjoint.";
      }
    }
    description
      "Type of the resource disjointness for a TE tunnel path.";
    reference
      "RFC4872: RSVP-TE Extensions in Support of End-to-End
       Generalized Multi-Protocol Label Switching (GMPLS)
       Recovery";
  } // te-path-disjointness

  typedef te-recovery-status {
    type enumeration {
      enum normal {
        description
          "Both the recovery and working spans are fully
           allocated and active, data traffic is being
           transported over (or selected from) the working
           span, and no trigger events are reported.";
      }
      enum recovery-started {
        description
          "The recovery action has been started, but not completed.";
      }
      enum recovery-succeeded {
        description
          "The recovery action has succeeded. The working span has
           reported a failure/degrade condition and the user traffic
           is being transported (or selected) on the recovery span.";
      }
      enum recovery-failed {
        description
          "The recovery action has failed.";
      }
      enum reversion-started {
        description
          "The reversion has started.";
      }
      enum reversion-succeeded {
        description
          "The reversion action has succeeded.";
      }
      enum reversion-failed {
        description
          "The reversion has failed.";
      }
      enum recovery-unavailable {
        description
          "The recovery is unavailable -- either as a result of an
           operator Lockout command or a failure condition detected
           on the recovery span.";
      }
      enum recovery-admin {
        description
          "The operator has issued a command switching the user
           traffic to the recovery span.";
      }
      enum wait-to-restore {
        description
          "The recovery domain is recovering from a failure/degrade
           condition on the working span that is being controlled by
           the Wait-to-Restore (WTR) timer.";
      }
    }
    description
      "Defines the status of a recovery action.";
    reference
      "RFC4427: Recovery (Protection and Restoration) Terminology
       for Generalized Multi-Protocol Label Switching (GMPLS).
       RFC6378: MPLS Transport Profile (MPLS-TP) Linear Protection";
  }

  typedef te-template-name {
    type string {
      pattern '/?([a-zA-Z0-9\-_.]+)(/[a-zA-Z0-9\-_.]+)*';
    }
    description
      "A type for the name of a TE node template or TE link
       template.";
  }

  typedef te-topology-event-type {
    type enumeration {
      enum "add" {
        value 0;
        description
          "A TE node or te-link has been added.";
      }
      enum "remove" {
        value 1;
        description
          "A TE node or te-link has been removed.";
      }
      enum "update" {
        value 2;
        description
          "A TE node or te-link has been updated.";
      }
    }
    description "TE Event type for notifications";
  } // te-topology-event-type

  typedef te-topology-id {
    type union {
        type string {
          length 0; // empty string
        }
        type string {
          pattern
            '([a-zA-Z0-9\-_.]+:)*'
          + '/?([a-zA-Z0-9\-_.]+)(/[a-zA-Z0-9\-_.]+)*';
        }
    }
    description
      "An identifier for a topology.
       It is optional to have one or more prefixes at the beginning,
       separated by colons. The prefixes can be the network-types,
       defined in ietf-network.yang, to help user to understand the
       topology better before further inquiry.";
    reference "RFC8345";
  }

  typedef te-tp-id {
    type union {
      type uint32;          // Unnumbered
      type inet:ip-address; // IPv4 or IPv6 address
    }
    description
      "An identifier for a TE link endpoint on a node.
       This attribute is mapped to local or remote link identifier in
       RFC3630 and RFC5305.";
  }

  /* TE features */
  feature p2mp-te {
    description
      "Indicates support for P2MP-TE";
    reference "RFC4875";
  }

  feature frr-te {
    description
      "Indicates support for TE FastReroute (FRR)";
    reference "RFC4090";
  }

  feature extended-admin-groups {
    description
      "Indicates support for TE link extended admin
      groups.";
    reference "RFC7308";
  }

  feature named-path-affinities {
    description
      "Indicates support for named path affinities";
  }

  feature named-extended-admin-groups {
    description
      "Indicates support for named extended admin groups";
  }

  feature named-srlg-groups {
    description
      "Indicates support for named SRLG groups";
  }

  feature named-path-constraints {
    description
      "Indicates support for named path constraints";
  }

  feature path-optimization-metric {
    description
      "Indicates support for path optimization metric";
  }

  feature path-optimization-objective-function {
    description
      "Indicates support for path optimization objective function";
  }

  /*
   * Identities
   */
  identity session-attributes-flags {
    description
      "Base identity for the RSVP-TE session attributes flags";
  }
  identity local-protection-desired {
    base session-attributes-flags;
    description "Fastreroute local protection is desired.";
    reference "RFC3209";
  }
  identity se-style-desired {
    description
      "Shared explicit style to allow the LSP to be
       established sharing resources with the old LSP.";
    reference "RFC3209";
  }
  identity local-recording-desired {
    description "Local recording desired";
    reference "RFC3209";
  }
  identity bandwidth-protection-desired {
    base session-attributes-flags;
    description
      "Request FRR bandwidth protection on LSRs if
      present.";
    reference "RFC4090";
  }
  identity node-protection-desired {
    base session-attributes-flags;
    description
      "Request FRR node protection on LSRs if
      present.";
    reference "RFC4090";
  }
  identity path-reevaluation-request {
    base session-attributes-flags;
    description
      "This flag indicates that a path re-evaluation (of the
       current path in use) is requested. Note that this does
       not trigger any LSP Reroute but instead just signals a
       request to evaluate whether a preferable path exists.";
    reference "RFC4736";
  }
  identity soft-preemption-desired {
    base session-attributes-flags;
    description
      "Soft-preemption of LSP resources is desired";
    reference "RFC5712";
  }

  identity lsp-attributes-flags {
    description "Base identity for per hop attribute flags";
  }
  identity end-to-end-rerouting-desired {
    base lsp-attributes-flags;
    description
      "Indicates end-to-end re-routing behavior for an
       LSP under establishment.  This MAY also be used for
       specifying the behavior of end-to-end LSP recovery for
       established LSPs.";
    reference "RFC4920, RFC5420, RFC7570";
  }
  identity boundary-rerouting-desired {
    base lsp-attributes-flags;
    description
      "Indicates boundary re-routing behavior for an LSP under
       establishment. This MAY also be used for specifying the
       segment-based LSP recovery through nested crankback for
       established LSPs.  The boundary ABR/ASBR can either decide
       to forward the PathErr message upstream to an upstream boundary
       ABR/ASBR or to the ingress LSR.
       Alternatively, it can try to select another egress boundary
       LSR.";
    reference "RFC4920, RFC5420, RFC7570";
  }
  identity segment-based-rerouting-desired {
    base lsp-attributes-flags;
    description
      "Indicates segment-based re-routing behavior for an LSP under
       establishment. This MAY also be used to specify the segment-
       based LSP recovery for established LSPs.";
    reference "RFC4920, RFC5420, RFC7570";
  }
  identity lsp-integrity-required {
    base lsp-attributes-flags;
    description "Indicates LSP integrity is required";
    reference "RFC4875, RFC7570";

  }
  identity contiguous-lsp-desired {
    base lsp-attributes-flags;
    description "Indicates contiguous LSP is desired";
    reference "RFC5151, RFC7570";
  }
  identity lsp-stitching-desired {
    base lsp-attributes-flags;
    description "Indicates LSP stitching is desired";
    reference "RFC5150, RFC7570";
  }
  identity pre-planned-lsp-flag {
    base lsp-attributes-flags;
    description
      "Indicates the LSP MUST be provisioned in the
       control plane only.";
    reference "RFC6001, RFC7570";
  }
  identity non-php-behavior-flag {
    base lsp-attributes-flags;
    description
      "Indicates non-php behavior for the LSP is desired";
    reference "RFC6511, RFC7570";
  }
  identity oob-mapping-flag {
    base lsp-attributes-flags;
    description
      "Indicates signaling of the egress binding information
       is out-of-band , (e.g., via Border Gateway Protocol (BGP))";
    reference "RFC6511, RFC7570";
  }
  identity entropy-label-capability {
    base lsp-attributes-flags;
    description "Indicates entropy label capability";
    reference "RFC6790, RFC7570";
  }
  identity oam-mep-entity-desired {
    base lsp-attributes-flags;
    description "OAM MEP entities desired";
    reference "RFC7260";
  }
  identity oam-mip-entity-desired {
    base lsp-attributes-flags;
    description "OAM MIP entities desired";
    reference "RFC7260";
  }
  identity srlg-collection-desired {
    base lsp-attributes-flags;
    description "SRLG collection desired";
    reference "RFC8001, RFC7570";
  }
  identity loopback-desired {
    base lsp-attributes-flags;
    description
      "This flag indicates a particular node on the LSP is
       required to enter loopback mode.  This can also be
       used for specifying the loopback state of the node.";
    reference "RFC7571";
  }
  identity p2mp-te-tree-eval-request {
    base lsp-attributes-flags;
    description "P2MP-TE tree re-evaluation request";
    reference "RFC8149";
  }
  identity rtm-set-desired {
    base lsp-attributes-flags;
    description
      "Residence Time Measurement (RTM) attribute flag";
    reference "RFC8169";
  }

  identity link-protection-type {
    description "Base identity for link protection type.";
  }
  identity link-protection-unprotected {
    base link-protection-type;
    description "Unprotected link type";
    reference "RFC4872";
  }
  identity link-protection-extra-traffic {
    base link-protection-type;
    description "Extra-traffic protected link type";
    reference "RFC4427.";
  }
  identity link-protection-shared {
    base link-protection-type;
    description "Shared protected link type";
    reference "RFC4872";
  }
  identity link-protection-1-for-1 {
    base link-protection-type;
    description "One for one protected link type";
    reference "RFC4872";
  }
  identity link-protection-1-plus-1 {
    base link-protection-type;
    description "One plus one protected link type";
    reference "RFC4872";
  }
  identity link-protection-enhanced {
    base link-protection-type;
    description "Enhanced protection protected link type";
    reference "RFC4872";
  }

  identity association-type {
    description "Base identity for tunnel association";
  }
  identity association-type-recovery {
    base association-type;
    description
      "Association Type Recovery used to association LSPs of
       same tunnel for recovery";
    reference "RFC6780, RFC4872";
  }
  identity association-type-resource-sharing {
    base association-type;
    description
      "Association Type Resource Sharing used to enable resource
       sharing during make-before-break.";
    reference "RFC6780, RFC4873";
  }
  identity association-type-double-sided-bidir {
    base association-type;
    description
      "Association Type Double Sided bidirectional used to associate
       two LSPs of two tunnels that are independently configured on
       either endpoint";
    reference "RFC7551";
  }
  identity association-type-single-sided-bidir {
    base association-type;
    description
      "Association Type Single Sided bidirectional used to associate
       two LSPs of two tunnels, where a tunnel is configured on one
       side/endpoint, and the other tunnel is dynamically created on
       the other endpoint";
    reference "RFC6780,RFC7551";
  }

  identity objective-function-type {
    description "Base objective function type";
  }
  identity of-minimize-cost-path {
    base objective-function-type;
    description
        "Minimize cost of path objective function";
    reference "RFC5541";
  }
  identity of-minimize-load-path {
    base objective-function-type;
    description
        "Minimize the load on path(s) objective
         function";
    reference "RFC5541";
  }
  identity of-maximize-residual-bandwidth {
    base objective-function-type;
    description
        "Maximize the residual bandwidth objective
         function";
    reference "RFC5541";
  }
  identity of-minimize-agg-bandwidth-consumption {
    base objective-function-type;
    description
        "minimize the aggregate bandwidth consumption
         objective function";
    reference "RFC5541";
  }
  identity of-minimize-load-most-loaded-link {
    base objective-function-type;
    description
        "Minimize the load on the most loaded link
         objective function";
    reference "RFC5541";
  }
  identity of-minimize-cost-path-set {
    base objective-function-type;
    description
        "Minimize the cost on a path set objective
         function";
    reference "RFC5541";
  }

  identity path-computation-method {
    description
     "base identity for supported path computation
      mechanisms";
  }
  identity path-locally-computed {
    base path-computation-method;
    description
      "indicates a constrained-path LSP in which the
      path is computed by the local LER";
    reference "RFC3209";
  }
  identity path-externally-queried {
    base path-computation-method;
    description
     "Constrained-path LSP in which the path is
      obtained by querying an external source, such as a PCE server.
      In the case that an LSP is defined to be externally queried, it
      may also have associated explicit definitions (provided
      to the external source to aid computation); and the path that is
      returned by the external source is not required to provide a
      wholly resolved path back to the originating system - that is to
      say, some local computation may also be required";
    reference "RFC4657";
  }
  identity path-explicitly-defined {
    base path-computation-method;
    description
     "constrained-path LSP in which the path is
      explicitly specified as a collection of strict or/and loose
      hops";
    reference "RFC3209";
  }

  identity lsp-metric-type {
    description
      "Base identity for types of LSP metric specification";
  }
  identity lsp-metric-relative {
    base lsp-metric-type;
    description
      "The metric specified for the LSPs to which this identity refers
      is specified as a relative value to the IGP metric cost to the
      LSP's tail-end.";
    reference "RFC4657";
  }
  identity lsp-metric-absolute {
    base lsp-metric-type;
    description
      "The metric specified for the LSPs to which this identity refers
      is specified as an absolute value";
    reference "RFC4657";
  }
  identity lsp-metric-inherited {
    base lsp-metric-type;
    description
      "The metric for the LSPs to which this identity refers is
      not specified explicitly - but rather inherited from the IGP
      cost directly";
    reference "RFC4657";
  }

  identity te-tunnel-type {
    description
      "Base identity from which specific tunnel types are
      derived.";
  }
  identity te-tunnel-p2p {
    base te-tunnel-type;
    description
      "TE point-to-point tunnel type.";
    reference "RFC3209";
  }
  identity te-tunnel-p2mp {
    base te-tunnel-type;
    description
      "TE point-to-multipoint tunnel type.";
    reference "RFC4875";
  }

  // NSO-REMOVED START
  // identity tunnel-action-type {
  //   description
  //     "Base identity from which specific tunnel action types
  //      are derived.";
  // }
  // identity tunnel-action-resetup {
  //   base tunnel-action-type;
  //   description
  //     "TE tunnel action resetup. Tears the
  //     tunnel's current LSP (if any) and
  //     attempts to re-establish a new LSP";
  // }
  // identity tunnel-action-reoptimize {
  //   base tunnel-action-type;
  //   description
  //     "TE tunnel action reoptimize.
  //      Reoptimizes placement of the tunnel LSP(s)";
  // }
  // identity tunnel-action-switchpath {
  //   base tunnel-action-type;
  //   description
  //     "TE tunnel action switchpath
  //      Switches the tunnel's LSP to use the specified path";
  // }

  // identity te-action-result {
  //   description
  //     "Base identity from which specific TE action results
  //      are derived.";
  // }
  // identity te-action-success {
  //   base te-action-result;
  //   description "TE action successful.";
  // }
  // identity te-action-fail {
  //   base te-action-result;
  //   description "TE action failed.";
  // }
  // identity tunnel-action-inprogress {
  //   base te-action-result;
  //   description "TE action inprogress.";
  // }
  // NSO-REMOVED END

  identity tunnel-admin-state-type {
    description
      "Base identity for TE tunnel admin states";
  }
  identity tunnel-admin-state-up {
    base tunnel-admin-state-type;
    description "Tunnel administratively state up";
  }
  identity tunnel-admin-state-down {
    base tunnel-admin-state-type;
    description "Tunnel administratively state down";
  }

  identity tunnel-state-type {
    description
      "Base identity for TE tunnel states";
  }
  identity tunnel-state-up {
    base tunnel-state-type;
    description "Tunnel state up";
  }
  identity tunnel-state-down {
    base tunnel-state-type;
    description "Tunnel state down";
  }

  identity lsp-state-type {
    description
      "Base identity for TE LSP states";
  }
  identity lsp-path-computing {
    base lsp-state-type;
    description
      "State path compute in progress";
  }
  identity lsp-path-computation-ok {
    base lsp-state-type;
    description
      "State path compute successful";
  }
  identity lsp-path-computation-failed {
    base lsp-state-type;
    description
      "State path compute failed";
  }
  identity lsp-state-setting-up {
    base lsp-state-type;
    description
      "State setting up";
  }
  identity lsp-state-setup-ok {
    base lsp-state-type;
    description
      "State setup successful";
  }
  identity lsp-state-setup-failed {
    base lsp-state-type;
    description
      "State setup failed";
  }
  identity lsp-state-up {
    base lsp-state-type;
    description "State up";
  }
  identity lsp-state-tearing-down {
    base lsp-state-type;
    description
      "State tearing down";
  }
  identity lsp-state-down {
    base lsp-state-type;
    description "State down";
  }

  identity path-invalidation-action-type {
    description
      "Base identity for TE path invalidation action types";
  }
  identity path-invalidation-action-drop-type {
    base path-invalidation-action-type;
    description
      "TE path invalidation action drop";
  }
  identity path-invalidation-action-drop-tear {
    base path-invalidation-action-type;
    description
      "TE path invalidation action tear";
  }

  identity lsp-restoration-type {
    description
      "Base identity from which LSP restoration types are
       derived.";
  }
  identity lsp-restoration-restore-any {
    base lsp-restoration-type;
    description
      "Restores when any of the LSPs is affected by a failure";
  }
  identity lsp-restoration-restore-all {
    base lsp-restoration-type;
    description
      "Restores when all the tunnel LSPs are affected by failure";
  }

  identity restoration-scheme-type {
    description
      "Base identity for LSP restoration schemes";
  }
  identity restoration-scheme-preconfigured {
    base restoration-scheme-type;
    description
      "Restoration LSP is preconfigured prior to the failure";
    reference "RFC4427";
  }
  identity restoration-scheme-precomputed {
    base restoration-scheme-type;
    description
      "Restoration LSP is precomputed prior to the failure";
    reference "RFC4427";
  }
  identity restoration-scheme-presignaled {
    base restoration-scheme-type;
    description
      "Restoration LSP is presignaled prior to the failure";
    reference "RFC4427";
  }

  identity lsp-protection-type {
    description
      "Base identity from which LSP protection types are
      derived.";
    reference "RFC4872";
  }
  identity lsp-protection-unprotected {
    base lsp-protection-type;
    description
      "LSP protection 'Unprotected'";
    reference "RFC4872";
  }
  identity lsp-protection-reroute-extra {
    base lsp-protection-type;
    description
      "LSP protection '(Full) Rerouting'";
    reference "RFC4872";
  }
  identity lsp-protection-reroute {
    base lsp-protection-type;
    description
      "LSP protection 'Rerouting without Extra-Traffic'";
    reference "RFC4872";
  }
  identity lsp-protection-1-for-n {
    base lsp-protection-type;
    description
      "LSP protection '1:N Protection with Extra-Traffic'";
    reference "RFC4872";
  }
  identity lsp-protection-unidir-1-for-1 {
    base lsp-protection-type;
    description
      "LSP protection '1:1 Unidirectional Protection'";
    reference "RFC4872";
  }
  identity lsp-protection-bidir-1-for-1 {
    base lsp-protection-type;
    description
      "LSP protection '1:1 Bidirectional Protection'";
    reference "RFC4872";
  }
  identity lsp-protection-unidir-1-plus-1 {
    base lsp-protection-type;
    description
      "LSP protection '1+1 Unidirectional Protection'";
    reference "RFC4872";
  }
  identity lsp-protection-bidir-1-plus-1 {
    base lsp-protection-type;
    description
      "LSP protection '1+1 Bidirectional Protection'";
    reference "RFC4872";
  }
  identity lsp-protection-extra-traffic {
    base lsp-protection-type;
    description
      "LSP protection 'Extra-Traffic'";
    reference
      "RFC4427.";
  }

  identity lsp-protection-state {
    description
      "Base identity of protection states for reporting
       purposes.";
  }
  identity normal {
    base lsp-protection-state;
    description "Normal state.";
  }
  identity signal-fail-of-protection {
    base lsp-protection-state;
    description
        "There is a signal fail condition on the protection
         transport entity which has higher priority than the
         forced switch command.";
    reference
        "RFC4427";
  }
  identity lockout-of-protection {
    base lsp-protection-state;
    description
        "A Loss of Protection (LoP) command is active.";
    reference
        "RFC4427";
  }
  identity forced-switch {
    base lsp-protection-state;
    description
        "A forced switch command is active.";
    reference
        "RFC4427";
  }
  identity signal-fail {
    base lsp-protection-state;
    description
        "There is a signal fail condition on either the working
        or the protection path.";
    reference
        "RFC4427";
  }
  identity signal-degrade {
    base lsp-protection-state;
    description
        "There is an signal degrade condition on either the working
         or the protection path.";
    reference
        "RFC4427";
  }
  identity manual-switch {
    base lsp-protection-state;
    description
        "A manual switch command is active.";
    reference
        "RFC4427";
  }
  identity wait-to-restore {
    base lsp-protection-state;
    description
        "A wait time to restore (WTR) is running.";
    reference
        "RFC4427";
  }
  identity do-not-revert {
    base lsp-protection-state;
    description
        "A DNR condition is active because of a non-revertive
         behavior.";
    reference
        "RFC4427";
  }
  identity failure-of-protocol {
    base lsp-protection-state;
    description
        "The protection is not working because of a failure of
         protocol condition.";
    reference
        "RFC4427";
  }

  // NSO-REMOVED START 
  // identity protection-external-commands {
  //   description
  //     "Base identity from which protection external commands
  //      for trouble shooting purposes are derived.";
  // }
  // identity action-freeze {
  //   base protection-external-commands;
  //   description
  //     "A temporary configuration action initiated by an operator
  //      command to prevent any switch action to be taken and as such
  //      freezes the current state.";
  //   reference
  //     "RFC4427";
  // }
  // identity clear-freeze {
  //   base protection-external-commands;
  //   description
  //     "An action that clears the active freeze state.";
  //   reference
  //     "RFC4427";
  // }
  // identity action-lockout-of-normal {
  //   base protection-external-commands;
  //   description
  //     "A temporary configuration action initiated by an operator
  //      command to ensure that the normal traffic is not allowed
  //      to use the protection transport entity.";
  //   reference
  //     "RFC4427";
  // }
  // identity clear-lockout-of-normal {
  //   base protection-external-commands;
  //   description
  //     "An action that clears the active lockout of normal state.";
  //   reference
  //     "RFC4427";
  // }
  // identity action-lockout-of-protection {
  //   base protection-external-commands;
  //   description
  //     "A temporary configuration action initiated by an operator
  //      command to ensure that the protection transport entity is
  //      temporarily not available to transport a traffic signal
  //      (either normal or extra traffic).";
  //   reference
  //       "RFC4427";
  // }
  // identity action-forced-switch {
  //   base protection-external-commands;
  //   description
  //       "A switch action initiated by an operator command to switch
  //        the extra traffic signal, the normal traffic signal, or the
  //        null signal to the protection transport entity, unless an
  //        equal or higher priority switch command is in effect.";
  //   reference
  //       "RFC4427";
  // }
  // identity action-manual-switch {
  //   base protection-external-commands;
  //   description
  //       "A switch action initiated by an operator command to switch
  //        the extra traffic signal, the normal traffic signal, or
  //        the null signal to the protection transport entity, unless
  //        a fault condition exists on other transport entities or an
  //        equal or higher priority switch command is in effect.";
  //   reference
  //       "RFC4427";
  // }
  // identity action-exercise {
  //   base protection-external-commands;
  //   description
  //       "An action to start testing if the APS communication is
  //        operating correctly. It is lower priority than any other
  //        state or command.";
  //   reference
  //       "RFC4427";
  // }
  // identity clear {
  //   base protection-external-commands;
  //   description
  //       "An action that clears the active near-end lockout of
  //        protection, forced switch, manual switch, WTR state,
  //        or exercise command.";
  //   reference
  //       "RFC4427";
  // }
  // NSO-REMOVED END

  identity switching-capabilities {
    description
      "Base identity for interface switching capabilities";
    reference "RFC3471";
  }
  identity switching-psc1 {
    base switching-capabilities;
    description
      "Packet-Switch Capable-1 (PSC-1)";
    reference "RFC3471";
  }
  identity switching-evpl {
    base switching-capabilities;
    description
      "Ethernet Virtual Private Line (EVPL)";
    reference "RFC6004";
  }
  identity switching-l2sc {
    base switching-capabilities;
    description
      "Layer-2 Switch Capable (L2SC)";
    reference "RFC3471";
  }
  identity switching-tdm {
    base switching-capabilities;
    description
      "Time-Division-Multiplex Capable (TDM)";
    reference "RFC3471";
  }
  identity switching-otn {
    base switching-capabilities;
    description
      "OTN-TDM capable";
    reference "RFC7138";
  }
  identity switching-dcsc {
    base switching-capabilities;
    description
      "Data Channel Switching Capable (DCSC)";
    reference "RFC6002";
  }
  identity switching-lsc {
    base switching-capabilities;
    description
      "Lambda-Switch Capable (LSC)";
    reference "RFC3471";
  }
  identity switching-fsc {
    base switching-capabilities;
    description
      "Fiber-Switch Capable (FSC)";
    reference "RFC3471";
  }

  identity lsp-encoding-types {
    description
      "Base identity for encoding types";
    reference "RFC3471";
  }
  identity lsp-encoding-packet {
    base lsp-encoding-types;
    description
      "Packet LSP encoding";
    reference "RFC3471";
  }
  identity lsp-encoding-ethernet {
    base lsp-encoding-types;
    description
      "Ethernet LSP encoding";
    reference "RFC3471";
  }
  identity lsp-encoding-pdh {
    base lsp-encoding-types;
    description
      "ANSI/ETSI LSP encoding";
    reference "RFC3471";
  }
  identity lsp-encoding-sdh {
    base lsp-encoding-types;
    description
      "SDH ITU-T G.707 / SONET ANSI T1.105 LSP encoding";
    reference "RFC3471";
  }
  identity lsp-encoding-digital-wrapper {
    base lsp-encoding-types;
    description
      "Digital Wrapper LSP encoding";
    reference "RFC3471";
  }
  identity lsp-encoding-lambda {
    base lsp-encoding-types;
    description
      "Lambda (photonic) LSP encoding";
    reference "RFC3471";
  }
  identity lsp-encoding-fiber {
    base lsp-encoding-types;
    description
      "Fiber LSP encoding";
    reference "RFC3471";
  }
  identity lsp-encoding-fiber-channel {
    base lsp-encoding-types;
    description
      "Fiber Channel LSP encoding";
    reference "RFC3471";
  }
  identity lsp-encoding-oduk {
    base lsp-encoding-types;
    description
      "G.709 ODUk (Digital Path) LSP encoding";
    reference "RFC4328";
  }
  identity lsp-encoding-optical-channel {
    base lsp-encoding-types;
    description
      "G.709 Optical Channel LSP encoding";
    reference "RFC4328";
  }
  identity lsp-encoding-line {
    base lsp-encoding-types;
    description
      "Line (e.g., 8B/10B) LSP encoding";
      reference "RFC6004";
  }

  identity path-signaling-type {
    description
      "base identity from which specific LSPs path
       setup types are derived";
  }
  identity path-setup-static {
    base path-signaling-type;
    description
      "Static LSP provisioning path setup";
  }
  identity path-setup-rsvp {
    base path-signaling-type;
    description
      "RSVP-TE signaling path setup";
    reference "RFC3209";
  }
  identity path-setup-sr {
    base path-signaling-type;
    description
      "Segment-routing path setup";
  }

  identity path-scope-type {
    description
      "base identity from which specific path
       scope types are derived";
  }
  identity path-scope-segment {
    base path-scope-type;
    description
      "Path scope segment";
    reference "RFC4873";
  }
  identity path-scope-end-to-end {
    base path-scope-type;
    description
      "Path scope end to end";
    reference "RFC4873";
  }

  identity route-usage-type {
    description
      "Base identity for route usage";
  }
  identity route-include-object {
    base route-usage-type;
    description
      "Include route object";
  }
  identity route-exclude-object {
    base route-usage-type;
    description
      "Exclude route object";
    reference "RFC4874";
  }
  identity route-exclude-srlg {
    base route-usage-type;
    description "Exclude SRLG";
    reference "RFC4874";
  }

  identity path-metric-type {
    description
      "Base identity for path metric type";
  }
  identity path-metric-te {
    base path-metric-type;
    description
      "TE path metric";
    reference "RFC3785";
  }
  identity path-metric-igp {
    base path-metric-type;
    description
      "IGP path metric";
    reference "RFC3785";
  }
  identity path-metric-hop {
    base path-metric-type;
    description
      "Hop path metric";
  }
  identity path-metric-delay-average {
    base path-metric-type;
    description
      "Unidirectional average link delay";
    reference "RFC7471";
  }
  identity path-metric-delay-minimum {
    base path-metric-type;
    description
      "Unidirectional minimum link delay";
    reference "RFC7471";
  }
  identity path-metric-residual-bandwidth {
    base path-metric-type;
    description
      "Unidirectional Residual Bandwidth, which is defined to be
       Maximum Bandwidth [RFC3630] minus the bandwidth currently
       allocated to LSPs.";
    reference "RFC7471";
  }
  identity path-metric-optimize-includes {
    base path-metric-type;
    description
      "A metric that optimizes the number of included resources
       specified in a set";
  }
  identity path-metric-optimize-excludes {
    base path-metric-type;
    description
      "A metric that optimizes the number of excluded resources
       specified in a set";
  }

  identity path-tiebreaker-type {
    description
      "Base identity for path tie-breaker type";
  }
  identity path-tiebreaker-minfill {
    base path-tiebreaker-type;
    description
      "Min-Fill LSP path placement";
  }
  identity path-tiebreaker-maxfill {
    base path-tiebreaker-type;
    description
      "Max-Fill LSP path placement";
  }
  identity path-tiebreaker-random {
    base path-tiebreaker-type;
    description
      "Random LSP path placement";
  }

  identity resource-affinities-type {
    description
      "Base identity for resource affinities";
    reference "RFC2702";
  }
  identity resource-aff-include-all {
    base resource-affinities-type;
    description
      "The set of attribute filters associated with a
      tunnel all of which must be present for a link
      to be acceptable";
    reference "RFC2702 and RFC3209";
  }
  identity resource-aff-include-any {
    base resource-affinities-type;
    description
      "The set of attribute filters associated with a
      tunnel any of which must be present for a link
      to be acceptable";
    reference "RFC2702 and RFC3209";
  }
  identity resource-aff-exclude-any {
    base resource-affinities-type;
    description
      "The set of attribute filters associated with a
      tunnel any of which renders a link unacceptable";
    reference "RFC2702 and RFC3209";
  }

  identity te-optimization-criterion {
    description
      "Base identity for TE optimization criterion.";
    reference
      "RFC3272: Overview and Principles of Internet Traffic
       Engineering.";
  }
  identity not-optimized {
    base te-optimization-criterion;
    description "Optimization is not applied.";
  }
  identity cost {
    base te-optimization-criterion;
    description "Optimized on cost.";
    reference "RFC5541";
  }
  identity delay {
    base te-optimization-criterion;
    description "Optimized on delay.";
    reference "RFC5541";
  }

  identity path-computation-srlg-type {
    description
      "Base identity for SRLG path computation";
  }
  identity srlg-ignore {
    base path-computation-srlg-type;
    description
      "Ignores SRLGs in path computation";
  }
  identity srlg-strict {
    base path-computation-srlg-type;
    description
      "Include strict SRLG check in path computation";
  }
  identity srlg-preferred {
    base path-computation-srlg-type;
    description
      "Include preferred SRLG check in path computation";
  }
  identity srlg-weighted {
    base path-computation-srlg-type;
    description
      "Include weighted SRLG check in path computation";
  }

  /**
   * TE bandwidth groupings
   **/
  grouping te-bandwidth {
    description
      "This grouping defines the generic TE bandwidth.
       For some known data plane technologies, specific modeling
       structures are specified. The string encoded te-bandwidth
       type is used for un-specified technologies.
       The modeling structure can be augmented later for other
       technologies.";
    container te-bandwidth {
      tailf:info "Container that specifies TE bandwidth. The choices
         can be augmented for specific dataplane technologies.";
      description
        "Container that specifies TE bandwidth. The choices
         can be augmented for specific dataplane technologies.";
      choice technology {
        default generic;
        description
          "Data plane technology type.";
        case generic {
          leaf generic {
            type te-bandwidth;
            tailf:info "Bandwidth specified in a generic format.";
            description
              "Bandwidth specified in a generic format.";
          }
        }
      }
    }
  }

  /**
   * TE label groupings
   **/
  grouping te-label {
    description
      "This grouping defines the generic TE label.
       The modeling structure can be augmented for each technology.
       For un-specified technologies, rt-types:generalized-label
       is used.";
    container te-label {
       tailf:info "Container that specifies TE label. The choices can
         be augmented for specific dataplane technologies.";
       description
        "Container that specifies TE label. The choices can
         be augmented for specific dataplane technologies.";
      choice technology {
        default generic;
        description
          "Data plane technology type.";
        case generic {
          leaf generic {
            type rt-types:generalized-label;
            tailf:info "TE label specified in a generic format.";
            description
              "TE label specified in a generic format.";
          }
        }
      }
      // NSO-REMOVED START
      // leaf direction {
      //   type te-label-direction;
      //   default 'forward';
      //   description "Label direction";
      // }
      // NSO-REMOVED END
    }
  }

  // NSO-REMOVED START
  // grouping te-topology-identifier {
  //   description
  //     "Augmentation for TE topology.";
  //   container te-topology-identifier {
  //     description "TE topology identifier container";
  //     leaf provider-id {
  //       type te-global-id;
  //       default 0;
  //       description
  //         "An identifier to uniquely identify a provider. If omitted,
  //          it assumes the default topology provider ID=0";
  //     }
  //     leaf client-id {
  //       type te-global-id;
  //       default 0;
  //       description
  //         "An identifier to uniquely identify a client. If omitted,
  //          it assumes the default topology client ID=0";
  //     }
  //     leaf topology-id {
  //       type te-topology-id;
  //       default '';
  //       description
  //         "When the datastore contains several topologies, the
  //          topology-id distinguishes between them. If omitted, the
  //          default empty string topology-id is assumed";
  //     }
  //   }
  // }

  /**
   * TE performance metric groupings
   **/
  // grouping performance-metrics-one-way-delay-loss {
  //   description
  //     "Performance Metric (PM) information in real time that can
  //     be applicable to links or connections. PM defined
  //     in this grouping is applicable to generic TE performance
  //     metrics as well as packet TE performance metrics.";
  //   reference
  //     "RFC7471: OSPF Traffic Engineering (TE) Metric Extensions.
  //     RFC8570: IS-IS Traffic Engineering (TE) Metric Extensions.
  //     RFC7823: Performance-Based Path Selection for Explicitly
  //     Routed Label Switched Paths (LSPs) Using TE Metric
  //     Extensions";
  //   leaf one-way-delay {
  //     type uint32 {
  //       range 0..16777215;
  //     }
  //     description "One-way delay or latency in micro seconds.";
  //   }
  //   leaf one-way-delay-normality {
  //     type te-types:performance-metrics-normality;
  //     description "One-way delay normality.";
  //   }
  // }

  // grouping performance-metrics-two-way-delay-loss {
  //   description
  //     "Performance metric information in real time that can
  //     be applicable to links or connections. PM defined
  //     in this grouping is applicable to generic TE performance
  //     metrics as well as packet TE performance metrics.";
  //   reference
  //     "RFC7471: OSPF Traffic Engineering (TE) Metric Extensions.
  //     RFC8570: IS-IS Traffic Engineering (TE) Metric Extensions.
  //     RFC7823: Performance-Based Path Selection for Explicitly
  //     Routed Label Switched Paths (LSPs) Using TE Metric
  //     Extensions";
  //   leaf two-way-delay {
  //     type uint32 {
  //       range 0..16777215;
  //     }
  //     description "Two-way delay or latency in micro seconds.";
  //   }
  //   leaf two-way-delay-normality {
  //     type te-types:performance-metrics-normality;
  //     description "Two-way delay normality.";
  //   }
  // }

  // grouping performance-metrics-one-way-bandwidth {
  //   description
  //     "Performance metric information in real time that can
  //     be applicable to links. PM defined
  //     in this grouping is applicable to generic TE performance
  //     metrics as well as packet TE performance metrics.";
  //   reference
  //     "RFC7471: OSPF Traffic Engineering (TE) Metric Extensions.
  //     RFC8570: IS-IS Traffic Engineering (TE) Metric Extensions.
  //     RFC7823: Performance-Based Path Selection for Explicitly
  //     Routed Label Switched Paths (LSPs) Using TE Metric
  //     Extensions";

  //   leaf one-way-residual-bandwidth {
  //     type rt-types:bandwidth-ieee-float32;
  //     default '0x0p0';
  //     description
  //       "Residual bandwidth that subtracts tunnel
  //        reservations from Maximum Bandwidth (or link capacity)
  //        [RFC3630] and provides an aggregated remainder across QoS
  //        classes.";
  //   }
  //   leaf one-way-residual-bandwidth-normality {
  //     type te-types:performance-metrics-normality;
  //     default 'normal';
  //     description "Residual bandwidth normality.";
  //   }
  //   leaf one-way-available-bandwidth {
  //     type rt-types:bandwidth-ieee-float32;
  //     default '0x0p0';
  //     description
  //       "Available bandwidth that is defined to be residual
  //        bandwidth minus the measured bandwidth used for the
  //        actual forwarding of non-RSVP-TE LSP packets.  For a
  //        bundled link, available bandwidth is defined to be the
  //        sum of the component link available bandwidths.";
  //   }
  //   leaf one-way-available-bandwidth-normality {
  //     type te-types:performance-metrics-normality;
  //     default 'normal';
  //     description "Available bandwidth normality.";
  //   }
  //   leaf one-way-utilized-bandwidth {
  //     type rt-types:bandwidth-ieee-float32;
  //     default '0x0p0';
  //     description
  //       "Bandwidth utilization that represents the actual
  //        utilization of the link (i.e. as measured in the router).
  //        For a bundled link, bandwidth utilization is defined to
  //        be the sum of the component link bandwidth
  //        utilizations.";
  //   }
  //   leaf one-way-utilized-bandwidth-normality {
  //     type te-types:performance-metrics-normality;
  //     default 'normal';
  //     description "Bandwidth utilization normality.";
  //   }
  // }

  // grouping one-way-performance-metrics {
  //   description
  //     "One-way performance metrics throttle grouping.";
  //   leaf one-way-delay {
  //     type uint32 {
  //       range 0..16777215;
  //     }
  //     default 0;
  //     description "One-way delay or latency in micro seconds.";
  //   }
  //   leaf one-way-residual-bandwidth {
  //     type rt-types:bandwidth-ieee-float32;
  //     default '0x0p0';
  //     description
  //       "Residual bandwidth that subtracts tunnel
  //        reservations from Maximum Bandwidth (or link capacity)
  //        [RFC3630] and provides an aggregated remainder across QoS
  //        classes.";
  //   }
  //   leaf one-way-available-bandwidth {
  //     type rt-types:bandwidth-ieee-float32;
  //     default '0x0p0';
  //     description
  //       "Available bandwidth that is defined to be residual
  //        bandwidth minus the measured bandwidth used for the
  //        actual forwarding of non-RSVP-TE LSP packets.  For a
  //        bundled link, available bandwidth is defined to be the
  //        sum of the component link available bandwidths.";
  //   }
  //   leaf one-way-utilized-bandwidth {
  //     type rt-types:bandwidth-ieee-float32;
  //     default '0x0p0';
  //     description
  //       "Bandwidth utilization that represents the actual
  //        utilization of the link (i.e. as measured in the router).
  //        For a bundled link, bandwidth utilization is defined to
  //        be the sum of the component link bandwidth
  //        utilizations.";
  //   }
  // }

  // grouping two-way-performance-metrics {
  //   description
  //     "Two-way performance metrics throttle grouping.";
  //   leaf two-way-delay {
  //     type uint32 {
  //       range 0..16777215;
  //     }
  //     default 0;
  //     description "Two-way delay or latency in micro seconds.";
  //   }
  // }

  // grouping performance-metrics-thresholds {
  //   description
  //     "Grouping for configurable thresholds for measured attributes";
  //   uses one-way-performance-metrics;
  //   uses two-way-performance-metrics;
  // }


  // grouping performance-metrics-attributes {
  //   description
  //     "A container containing performance metric attributes.";
  //   container performance-metrics-one-way {
  //     description
  //       "One-way link performance information in real time.";
  //     reference
  //       "RFC7471: OSPF Traffic Engineering (TE) Metric Extensions.
  //        RFC8570: IS-IS Traffic Engineering (TE) Metric Extensions.
  //        RFC7823: Performance-Based Path Selection for Explicitly
  //        Routed Label Switched Paths (LSPs) Using TE Metric
  //        Extensions";
  //     uses performance-metrics-one-way-delay-loss;
  //     uses performance-metrics-one-way-bandwidth;
  //   }
  //   container performance-metrics-two-way {
  //     description
  //       "Two-way link performance information in real time.";
  //     reference
  //       "RFC7471: OSPF Traffic Engineering (TE) Metric Extensions.
  //        RFC8570: IS-IS Traffic Engineering (TE) Metric Extensions.
  //        RFC7823: Performance-Based Path Selection for Explicitly
  //        Routed Label Switched Paths (LSPs) Using TE Metric
  //        Extensions";
  //     uses performance-metrics-two-way-delay-loss;
  //   }
  // }

  // grouping performance-metrics-throttle-container {
  //   description
  //     "A container controlling performance metric throttle.";
  //   container throttle {
  //     must "suppression-interval >= measure-interval" {
  //       error-message
  //         "suppression-interval cannot be less then
  //          measure-interval.";
  //       description
  //         "Constraint on suppression-interval and
  //          measure-interval.";
  //     }
  //     description
  //       "Link performance information in real time.";
  //     reference
  //       "RFC7471: OSPF Traffic Engineering (TE) Metric Extensions.
  //        RFC8570: IS-IS Traffic Engineering (TE) Metric Extensions.
  //        RFC7823: Performance-Based Path Selection for Explicitly
  //        Routed Label Switched Paths (LSPs) Using TE Metric
  //        Extensions";
  //     leaf one-way-delay-offset {
  //       type uint32 {
  //         range 0..16777215;
  //       }
  //       default 0;
  //       description
  //         "Offset value to be added to the measured delay value.";
  //     }
  //     leaf measure-interval {
  //       type uint32;
  //       default 30;
  //       description
  //         "Interval in seconds to measure the extended metric
  //          values.";
  //     }
  //     leaf advertisement-interval {
  //       type uint32;
  //       default 0;
  //       description
  //         "Interval in seconds to advertise the extended metric
  //          values.";
  //     }
  //     leaf suppression-interval {
  //       type uint32 {
  //         range "1 .. max";
  //       }
  //       default 120;
  //       description
  //         "Interval in seconds to suppress advertising the extended
  //          metric values.";
  //     }
  //     container threshold-out {
  //       uses performance-metrics-thresholds;
  //       description
  //         "If the measured parameter falls outside an upper bound
  //          for all but the min delay metric (or lower bound for
  //          min-delay metric only) and the advertised value is not
  //          already outside that bound, anomalous announcement will be
  //          triggered.";
  //     }
  //     container threshold-in {
  //       uses performance-metrics-thresholds;
  //       description
  //         "If the measured parameter falls inside an upper bound
  //          for all but the min delay metric (or lower bound for
  //          min-delay metric only) and the advertised value is not
  //          already inside that bound, normal (anomalous-flag cleared)
  //          announcement will be triggered.";
  //     }
  //     container threshold-accelerated-advertisement {
  //       description
  //         "When the difference between the last advertised value and
  //          current measured value exceed this threshold, anomalous
  //          announcement will be triggered.";
  //       uses performance-metrics-thresholds;
  //     }
  //   }
  // } // performance-metrics-throttle-container
  // NSO-REMOVED END

  /**
   * TE tunnel generic groupings
   **/
  grouping explicit-route-hop {
    description
      "The explicit route entry grouping";
    choice type {
      description
        "The explicit route entry type";
      case numbered-node-hop {
        container numbered-node-hop {
          leaf node-id {
            type te-node-id;
            mandatory true;
            tailf:info "The identifier of a node in the TE topology.";
            description
              "The identifier of a node in the TE topology.";
          }
          leaf hop-type {
            type te-hop-type;
            default 'strict';
            tailf:info "strict or loose hop";
            description "strict or loose hop";
          }
          tailf:info "Numbered node route hop";
          description "Numbered node route hop";
          reference
            "RFC3209: section 4.3 for EXPLICIT_ROUTE in RSVP-TE
             RFC3477: Signalling Unnumbered Links in RSVP-TE";
        }
      }
      // NSO-REMOVED START
      // case numbered-link-hop {
      //   container numbered-link-hop {
      //     leaf link-tp-id {
      //       type te-tp-id;
      //       mandatory true;
      //       tailf:info "TE link termination point identifier.";
      //       description
      //         "TE link termination point identifier.";
      //     }
      //     leaf hop-type {
      //       type te-hop-type;
      //       default 'strict';
      //       tailf:info "strict or loose hop";
      //       description "strict or loose hop";
      //     }
      //     leaf direction {
      //       type te-link-direction;
      //       default 'outgoing';
      //       tailf:info "Link route object direction";
      //       description "Link route object direction";
      //     }
      //     tailf:info "Numbered link explicit route hop";
      //     description
      //       "Numbered link explicit route hop";
      //     reference
      //       "RFC3209: section 4.3 for EXPLICIT_ROUTE in RSVP-TE
      //        RFC3477: Signalling Unnumbered Links in RSVP-TE";
      //   }
      // }
      // case unnumbered-link-hop {
      //   container unnumbered-link-hop {
      //     leaf link-tp-id {
      //       type te-tp-id;
      //       mandatory true;
      //       tailf:info "TE link termination point identifier. The combination
      //          of TE link ID and the TE node ID is used to identify an
      //          unnumbered TE link.";
      //       description
      //         "TE link termination point identifier. The combination
      //          of TE link ID and the TE node ID is used to identify an
      //          unnumbered TE link.";
      //     }
      //     leaf node-id {
      //       type te-node-id;
      //       mandatory true;
      //       tailf:info "The identifier of a node in the TE topology.";
      //       description
      //         "The identifier of a node in the TE topology.";
      //     }
      //     leaf hop-type {
      //       type te-hop-type;
      //       default 'strict';
      //       tailf:info "strict or loose hop";
      //       description "strict or loose hop";
      //     }
      //     leaf direction {
      //       type te-link-direction;
      //       default 'outgoing';
      //       tailf:info "Link route object direction";
      //       description "Link route object direction";
      //     }
      //     tailf:info "Unnumbered link explicit route hop";
      //     description
      //       "Unnumbered link explicit route hop";
      //     reference
      //       "RFC3209: section 4.3 for EXPLICIT_ROUTE in RSVP-TE
      //        RFC3477: Signalling Unnumbered Links in RSVP-TE";
      //   }
      // }
      // case as-number {
      //   container as-number-hop {
      //     leaf as-number {
      //       type inet:as-number;
      //       mandatory true;
      //       tailf:info "The AS number";
      //       description "The AS number";
      //     }
      //     leaf hop-type {
      //       type te-hop-type;
      //       default 'strict';
      //       tailf:info "strict or loose hop";
      //       description "strict or loose hop";
      //     }
      //     tailf:info "Autonomous System explicit route hop";
      //     description
      //       "Autonomous System explicit route hop";
      //   }
      // }
      // NSO-REMOVED END
      case label {
        container label-hop {
          tailf:info "Label hop type";
          description "Label hop type";
          uses te-label;
        }
        description
          "The label explicit route hop type";
      }
    }
  }

  grouping record-route-state {
    description
      "The record route grouping";
    leaf index {
      type uint32;
      description
        "Record route hop index. The index is used to
         identify an entry in the list. The order of entries
         is defined by the user without relying on key values";
    }
    choice type {
      description
        "The record route entry type";
      case numbered-node-hop {
        container numbered-node-hop {
          description "Numbered node route hop container";
          leaf node-id {
            type te-node-id;
            mandatory true;
            description
              "The identifier of a node in the TE topology.";
          }
          leaf-list flags {
            type path-attribute-flags;
            description "Record route per hop flags";
            reference "RFC3209, RFC4090, RFC4561";
          }
        }
        description "Numbered node route hop";
      }
      case numbered-link-hop {
        container numbered-link-hop {
          description "Numbered link route hop container";
          leaf link-tp-id {
            type te-tp-id;
            mandatory true;
            description
              "Numbered TE link termination point identifier.";
          }
          leaf-list flags {
            type path-attribute-flags;
            description "Record route per hop flags";
            reference "RFC3209, RFC4090, RFC4561";
          }
        }
        description "Numbered link route hop";
      }
      // NSO-REMOVED START
      // case unnumbered-link-hop {
      //   container unnumbered-link-hop {
      //     leaf link-tp-id {
      //       type te-tp-id;
      //       mandatory true;
      //       description
      //           "TE link termination point identifier. The combination
      //            of TE link ID and the TE node ID is used to identify an
      //            unnumbered TE link.";
      //     }
      //     leaf node-id {
      //       type te-node-id;
      //       description
      //         "The identifier of a node in the TE topology.";
      //     }
      //     leaf-list flags {
      //       type path-attribute-flags;
      //       description "Record route per hop flags";
      //       reference "RFC3209, RFC4090, RFC4561";
      //     }
      //     description
      //       "Unnumbered link record route hop";
      //     reference
      //       "RFC3477: Signalling Unnumbered Links in
      //        RSVP-TE";
      //   }
      //   description "Unnumbered link route hop";
      // }
      // NSO-REMOVED END
      case label {
        container label-hop {
          description "Label route hop type";
          uses te-label;
          leaf-list flags {
            type path-attribute-flags;
            description "Record route per hop flags";
            reference "RFC3209, RFC4090, RFC4561";
          }
        }
        description
          "The Label record route entry types";
      }
    }
  }

  grouping label-restriction-info {
    description "Label set item info";
    leaf restriction {
      type enumeration {
        enum inclusive {
          description "The label or label range is inclusive.";
        }
        enum exclusive {
          description "The label or label range is exclusive.";
        }
      }
      default 'inclusive';
      description
        "Whether the list item is inclusive or exclusive.";
    }
    leaf index {
      type uint32;
      description
        "The index of the label restriction list entry.";
    }
    container label-start {
      must "(not(../label-end/te-label/direction) and" +
                    " not(te-label/direction))"
        + " or "
        +  "(../label-end/te-label/direction = te-label/direction)"
        + " or "
        +  "(not(te-label/direction) and" +
                    " (../label-end/te-label/direction = 'forward'))"
        + " or "
        +  "(not(../label-end/te-label/direction) and" +
                    " (te-label/direction = 'forward'))" {
        error-message
          "label-start and label-end must have the same direction.";
      }
      description
        "This is the starting label if a label range is specified.
         This is the label value if a single label is specified,
         in which case, attribute 'label-end' is not set.";
      uses te-label;
    }
    container label-end {
      must "(not(../label-start/te-label/direction) and" +
                    " not(te-label/direction))"
        + " or "
        +  "(../label-start/te-label/direction = te-label/direction)"
        + " or "
        +  "(not(te-label/direction) and" +
                    " (../label-start/te-label/direction = 'forward'))"
        + " or "
        +  "(not(../label-start/te-label/direction) and" +
                    " (te-label/direction = 'forward'))" {
        error-message
          "label-start and label-end must have the same direction.";
      }
      description
        "The ending label if a label range is specified;
         This attribute is not set, If a single label is
         specified.";
      uses te-label;
    }
    container label-step {
      description
        "The step increment between labels in the label range.
         The label start/end values will have to be consistent
         with the sign of label step. For example,
         label-start < label-end enforces label-step > 0
         label-start > label-end enforces label-step < 0";
      choice technology {
        default generic;
        description
          "Data plane technology type.";
        case generic {
          leaf generic {
            type int32;
            default 1;
            description "Label range step";
          }
        }
      }
    }
    leaf range-bitmap {
      type yang:hex-string;
      description
        "When there are gaps between label-start and label-end,
         this attribute is used to specify the positions
         of the used labels. This is represented in big-endian as
         hex-string.

         Each bit-position in the range-bitmap hex-string maps to a
         label in the range derived from the label-start.

         For example, assuming label-start=16000 and
         range-bitmap=0x01000001, then:
          - bit-position(0) is set, and the corresponding mapped label
            from the range is: 16000 + (0 * label-step) or
            16000 for default label-step=1.
          - bit-position(24) is set, and the corresponding mapped label
            from the range is: 16000 + (24 * label-step) or
            16024 for default label-step=1";
    }
  }

  grouping label-set-info {
    description
      "Grouping for List of label restrictions specifying what labels
       may or may not be used on a link connectivity.";
    container label-restrictions {
      description
        "The label restrictions container";
      list label-restriction {
        key "index";
        description
          "The absence of label-set implies that all labels are
           acceptable; otherwise only restricted labels are
           available.";
        reference
          "RFC7579: General Network Element Constraint Encoding
           for GMPLS-Controlled Networks";
        uses label-restriction-info;
      }
    }
  }

  grouping optimization-metric-entry {
    description "Optimization metrics configuration grouping";
    leaf metric-type {
      type identityref {
        base path-metric-type;
      }
      tailf:info "Identifies an entry in the list of metric-types to
         optimize the TE path for.";
      description
        "Identifies an entry in the list of metric-types to
         optimize the TE path for.";
    }

    // NSO-REMOVED START
    // leaf weight {
    //   type uint8;
    //   default 1;
    //   description "TE path metric normalization weight";
    // }
    // container explicit-route-exclude-objects {
    //   when "../metric-type = " +
    //        "'te-types:path-metric-optimize-excludes'";
    //   description
    //     "Container for the exclude route object list";
    //   uses path-route-exclude-objects;
    // }
    // container explicit-route-include-objects {
    //   when "../metric-type = " +
    //        "'te-types:path-metric-optimize-includes'";
    //   description
    //     "Container for the include route object list";
    //   uses path-route-include-objects;
    // }
    // NSO-REMOVED END
  }

  grouping common-constraints {
    description
      "Common constraints grouping that can be set on
       a constraint set or directly on the tunnel";

    uses te-bandwidth {
      description
        "A requested bandwidth to use for path computation";
    }
    // NSO-REMOVED START
    // leaf link-protection {
    //   type identityref {
    //     base link-protection-type;
    //   }
    //   default te-types:link-protection-unprotected;
    //   description
    //     "Link protection type required for the links included
    //      in the computed path";
    //   reference
    //     "RFC4202: Routing Extensions in Support of
    //      Generalized Multi-Protocol Label Switching (GMPLS).";
    // }
    // NSO-REMOVED END

    leaf setup-priority {
      tailf:info "<0-7> - TE LSP requested setup priority";
      description "<0-7> - TE LSP requested setup priority";
      type uint8 {
        range "0..7";
      }
      default 7;
      reference "RFC3209";
    }
    leaf hold-priority {
      tailf:info "<0-7> - TE LSP requested hold priority";
      description "<0-7> - TE LSP requested hold priority";
      type uint8 {
        range "0..7";
      }
      default 7;
      reference "RFC3209";
    }
    leaf signaling-type {
      type identityref {
        base path-signaling-type;
      }
      default te-types:path-setup-rsvp;
      tailf:info "path-setup-rsvp;; TE tunnel path signaling type.";
      description "path-setup-rsvp;; TE tunnel path signaling type.";
    }
  }

  grouping tunnel-constraints {
    description
      "Tunnel constraints grouping that can be set on
       a constraint set or directly on the tunnel";
    // NSO-REMOVED START
    // uses te-topology-identifier;
    // NSO-REMOVED END
    uses common-constraints;
  }

  grouping path-constraints-route-objects {
    description
      "List of route entries to be included or excluded when performing
       path computation.";
    container explicit-route-objects-always {
      tailf:info "Container for the exclude route object list";
      description
        "Container for the exclude route object list";
      // NSO-REMOVED START
      // list route-object-exclude-always {
      //   key index;
      //   ordered-by user;
      //   tailf:info "List of route objects to always exclude
      //      from path computation";
      //   description
      //     "List of route objects to always exclude
      //      from path computation";
      //   leaf index {
      //     type uint32;
      //     tailf:info "Explicit route object index. The index is used to
      //        identify an entry in the list. The order of entries
      //        is defined by the user without relying on key values";
      //     description
      //       "Explicit route object index. The index is used to
      //        identify an entry in the list. The order of entries
      //        is defined by the user without relying on key values";
      //   }
      //   uses explicit-route-hop;
      // }
      // NSO-REMOVED END
      list route-object-include-exclude {
        key index;
        ordered-by user;
        tailf:info "List of route objects to include or exclude in path
           computation";
        description
          "List of route objects to include or exclude in path
           computation";
        leaf explicit-route-usage {
          type identityref {
            base route-usage-type;
          }
          default te-types:route-include-object;
          tailf:info "Include or exclude usage. Default is to include";
          description
            "Include or exclude usage. Default is to include";
        }
        leaf index {
          type uint32;
          tailf:info
            "Route object include-exclude index Range <1-65535>. The index is used to
             identify an entry in the list. The order of entries
             is defined by the user without relying on key values";
          description
            "Route object include-exclude index <1-65535>. The index is used to
             identify an entry in the list. The order of entries
             is defined by the user without relying on key values";
        }
        uses explicit-route-hop {
          augment "type" {
            // NSO-REMOVED START
            // case srlg {
            //   container srlg {
            //     tailf:info "RLG container";
            //     description "SRLG container";
            //     leaf srlg {
            //       type uint32;
            //       tailf:info "SRLG value";
            //       description "SRLG value";
            //     }
            //   }
            //   description "An SRLG value to be included or excluded";
            // }
            // NSO-REMOVED END
            description
              "Augmentation to generic explicit route for SRLG
               exclusion";
          }
        }
      }
    }
  }

  // NSO-REMOVED START
  // grouping path-route-include-objects {
  //   description
  //     "List of route object(s) to be included when performing
  //      the path computation.";
  //   list route-object-include-object {
  //     key index;
  //     ordered-by user;
  //     description
  //       "List of explicit route objects to be included
  //        in path computation";
  //     leaf index {
  //       type uint32;
  //       description
  //         "Route object entry index. The index is used to
  //          identify an entry in the list. The order of entries
  //          is defined by the user without relying on key values";
  //     }
  //     uses explicit-route-hop;
  //   }
  // }

  // grouping path-route-exclude-objects {
  //   description
  //     "List of route object(s) to be excluded when performing
  //      the path computation.";
  //   list route-object-exclude-object {
  //     key index;
  //     ordered-by user;
  //     description
  //       "List of explicit route objects to be excluded
  //        in path computation";
  //     leaf index {
  //       type uint32;
  //       description
  //         "Route object entry index. The index is used to
  //          identify an entry in the list. The order of entries
  //          is defined by the user without relying on key values";
  //     }
  //     uses explicit-route-hop {
  //       augment "type" {
  //         case srlg {
  //           container srlg {
  //             description "SRLG container";
  //             leaf srlg {
  //               type uint32;
  //               description "SRLG value";
  //             }
  //           }
  //           description "An SRLG value to be included or excluded";
  //         }
  //         description
  //           "Augmentation to generic explicit route for SRLG exclusion";
  //       }
  //     }
  //   }
  // }
  // grouping generic-path-metric-bounds {
  //   description "TE path metric bounds grouping";
  //   container path-metric-bounds {
  //     description "TE path metric bounds container";
  //     list path-metric-bound {
  //       key metric-type;
  //       description "List of TE path metric bounds";
  //       leaf metric-type {
  //         type identityref {
  //           base path-metric-type;
  //         }
  //         description
  //           "Identifies an entry in the list of metric-types
  //            bound for the TE path.";
  //       }
  //       leaf upper-bound {
  //         type uint64;
  //         default 0;
  //         description
  //           "Upper bound on end-to-end TE path metric. A zero indicate
  //            an unbounded upper limit for the specific metric-type";
  //       }
  //     }
  //   }
  // }
  // NSO-REMOVED END

  grouping generic-path-optimization {
    description "TE generic path optimization grouping";

    container optimizations {
      tailf:info "The objective function container that includes
         attributes to impose when computing a TE path";
      description
        "The objective function container that includes
         attributes to impose when computing a TE path";

      choice algorithm {
        description "Optimizations algorithm.";
        case metric {
          if-feature path-optimization-metric;
          /* Optimize by metric */

          list optimization-metric {
            key "metric-type";
            tailf:info "TE path metric type.";
            description "TE path metric type.";
            uses optimization-metric-entry;
            must "not ((metric-type = 'te-types:path-metric-delay-minimum' or
                        metric-type = 'te-types:path-metric-delay-average')
                      and
                       ((contains(/ncs:devices/lsa-utils:lsa/lsa-utils:dispatch-map/lsa-utils:device
                        [lsa-utils:name=current()/../../../../head-end]
                        /lsa-utils:ned-id,'cisco-ios-cli-')) or
                        ((../../../../bidirectional = 'true') and
                        (contains(/ncs:devices/lsa-utils:lsa/lsa-utils:dispatch-map/lsa-utils:device
                        [lsa-utils:name=current()/../../../../tail-end]
                        /lsa-utils:ned-id, 'cisco-ios-cli-')))))" {
              error-message "Invalid input. Only path-metric-igp and "
                          + "path-metric-te are supported as metric-type for "
                          + "XE device.";
              tailf:dependency "metric-type";
              tailf:dependency "../../../../bidirectional";
              tailf:dependency "../../../../head-end";
              tailf:dependency "../../../../tail-end";
              tailf:dependency "/ncs:devices/lsa-utils:lsa/lsa-utils:dispatch-map/lsa-utils:device/lsa-utils:name";
              tailf:dependency "/ncs:devices/lsa-utils:lsa/lsa-utils:dispatch-map/lsa-utils:device/lsa-utils:ned-id";
            }
          }

          /* Tiebreakers */
          // NSO-REMOVED START
          // container tiebreakers {
          //   description
          //     "Container for the list of tiebreaker(s)";
          //   list tiebreaker {
          //     key "tiebreaker-type";
          //     description
          //       "The list of tiebreaker criterion to apply
          //        on an equally favored set of paths to pick best";
          //     leaf tiebreaker-type {
          //       type identityref {
          //         base path-metric-type;
          //       }
          //       description
          //         "Identifies an entry in the list of tiebreakers.";
          //     }
          //   }
          // }
          // NSO-REMOVED END
        }
        // NSO-REMOVED START
        // case objective-function {
        //   if-feature path-optimization-objective-function;
        //   // Objective functions
        //   container objective-function {
        //     description
        //       "The objective function container that includes
        //        attributes to impose when computing a TE path";
        //     leaf objective-function-type {
        //       type identityref {
        //         base objective-function-type;
        //       }
        //       default te-types:of-minimize-cost-path;
        //       description "Objective function entry";
        //     }
        //   }
        // }
        // NSO-REMOVED END
      }
    }
  }

  // NSO-REMOVED START
  // grouping generic-path-affinities {
  //   description
  //     "Path affinities grouping";
  //   container path-affinities-values {
  //     description
  //       "Path affinities values representation";
  //     list path-affinities-value {
  //       key "usage";
  //       description
  //         "List of named affinity constraints";
  //       leaf usage {
  //         type identityref {
  //           base resource-affinities-type;
  //         }
  //         description
  //           "Identifies an entry in the list of value affinities
  //            constraints";
  //       }
  //       leaf value {
  //         type admin-groups;
  //         default '';
  //         description "The affinity value. The default is empty.";
  //       }
  //     }
  //   }
  //   container path-affinity-names {
  //     description
  //       "Path affinities named representation style";
  //     list path-affinity-name {
  //       key "usage";
  //       description "List of named affinity constraints";
  //       leaf usage {
  //         type identityref {
  //           base resource-affinities-type;
  //         }
  //         description
  //           "Identifies an entry in the list of named affinities
  //            constraints";
  //       }
  //       list affinity-name {
  //         key "name";
  //         leaf name {
  //           type string;
  //           description "Identify a named affinity entry.";
  //         }
  //         description "List of named affinities";
  //       }
  //     }
  //   }
  // }
  // grouping generic-path-srlgs {
  //   description
  //     "Path SRLG grouping";
  //   container path-srlgs-lists {
  //     description
  //       "Path SRLG properties container";
  //     list path-srlgs-list {
  //       key "usage";
  //       description
  //         "List entries of value SRLGs to be included or excluded";
  //       leaf usage {
  //         type identityref {
  //           base route-usage-type;
  //         }
  //         description
  //           "Identifies an entry of list of SRLGs to either include
  //            or exclude";
  //       }
  //       leaf-list values {
  //         type srlg;
  //         description "List of SRLG values";
  //       }
  //     }
  //   }
  //   container path-srlgs-names {
  //     description "Container for named SRLG list";
  //     list path-srlgs-name {
  //       key "usage";
  //       description
  //         "List entries of named SRLGs to be included or excluded";
  //       leaf usage {
  //         type identityref {
  //           base route-usage-type;
  //         }
  //         description
  //           "Identifies an entry of list of named SRLGs to either
  //            include or exclude";
  //       }
  //       leaf-list names {
  //         type string;
  //         description "List named SRLGs";
  //       }
  //     }
  //   }
  // }
  // grouping generic-path-disjointness {
  //   description "Path disjointness grouping";
  //   leaf disjointness {
  //     type te-path-disjointness;
  //     description
  //       "The type of resource disjointness.
  //        Under primary path, disjointness level applies to
  //        all secondary LSPs. Under secondary, disjointness
  //        level overrides the one under primary";
  //   }
  // }
  // grouping common-path-constraints-attributes {
  //   description
  //     "Common path constraints configuration grouping";
  //   uses common-constraints;
  //   uses generic-path-metric-bounds;
  //   uses generic-path-affinities;
  //   uses generic-path-srlgs;
  // }

  // grouping generic-path-constraints {
  //   description
  //     "Global named path constraints configuration
  //     grouping";
  //   container path-constraints {
  //     description "TE named path constraints container";
  //     uses common-path-constraints-attributes;
  //     uses generic-path-disjointness;
  //   }
  // }

  // grouping generic-path-properties {
  //   description "TE generic path properties grouping";
  //   container path-properties {
  //     config false;
  //     description "The TE path properties";
  //     list path-metric {
  //       key metric-type;
  //       description "TE path metric type";
  //       leaf metric-type {
  //         type identityref {
  //           base path-metric-type;
  //         }
  //         description "TE path metric type";
  //       }
  //       leaf accumulative-value {
  //         type uint64;
  //         description "TE path metric accumulative value";
  //       }
  //     }
  //     uses generic-path-affinities;
  //     uses generic-path-srlgs;
  //     container path-route-objects {
  //       description
  //         "Container for the list of route objects either returned by
  //          the computation engine or actually used by an LSP";
  //       list path-route-object {
  //         key index;
  //         ordered-by user;
  //         description
  //           "List of route objects either returned by the computation
  //            engine or actually used by an LSP";
  //         leaf index {
  //           type uint32;
  //           description
  //             "Route object entry index. The index is used to
  //              identify an entry in the list. The order of entries
  //              is defined by the user without relying on key values";
  //         }
  //         uses explicit-route-hop;
  //       }
  //     }
  //   }
  // }
  // NSO-REMOVED END
}
