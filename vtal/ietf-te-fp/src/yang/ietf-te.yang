module ietf-te {
  yang-version 1.1;

  namespace "urn:ietf:params:xml:ns:yang:ietf-te";

  /* Replace with IANA when assigned */
  prefix "te";

  /* Import TE generic types */
  import ietf-te-types {
    prefix te-types;
    reference "draft-ietf-teas-yang-te-types: A YANG Data Model for
               Common Traffic Engineering Types";
  }

  import ietf-inet-types {
    prefix inet;
    reference "RFC6991: Common YANG Data Types";
  }

  import ietf-yang-types {
    prefix "yang";
    reference "RFC6991: Common YANG Data Types";
  }

  // NSO ADDITION - START
  import tailf-common { prefix tailf; }
  import tailf-ncs { prefix ncs; }
  import custom-template-hook { prefix ct-hook; }
  import tailf-kicker { prefix kicker; }
  import lsa-utils { prefix lsa-utils; }
  import cisco-tsdn-core-fp-common { prefix tsdn-core-fp-common; }
  // NSO ADDITION - END

  organization
    "IETF Traffic Engineering Architecture and Signaling (TEAS)
     Working Group";

  contact
    "WG Web:   <http://tools.ietf.org/wg/teas/>
     WG List:  <mailto:teas@ietf.org>

     WG Chair: Lou Berger
               <mailto:lberger@labn.net>

     WG Chair: Vishnu Pavan Beeram
               <mailto:vbeeram@juniper.net>

     Editor:   Tarek Saad
               <mailto:tsaad@juniper.net>

     Editor:   Rakesh Gandhi
               <mailto:rgandhi@cisco.com>

     Editor:   Vishnu Pavan Beeram
               <mailto:vbeeram@juniper.net>

     Editor:   Himanshu Shah
               <mailto:hshah@ciena.com>

     Editor:   Xufeng Liu
               <mailto: xufeng.liu.ietf@gmail.com>

     Editor:   Igor Bryskin
               <mailto:Igor.Bryskin@huawei.com>";

  description
    "YANG data module for TE configuration,
    state, RPC and notifications.";

  revision 2022-08-12 {
    description "Modified default value for iosxr-default-ned-id to cisco-iosxr-cli-7.40";
  }

  revision 2022-05-04 {
    description "Modified default value for iosxr-default-ned-id to cisco-iosxr-cli-7.39";
  }

  revision 2022-01-13 {
    description "Modified default value for iosxr-default-ned-id to cisco-iosxr-cli-7.38";
  }

  revision 2021-12-03 {
	description
	  "Removed: core-fp-common reference
	   Modified: Read dispatch-map using lsa-utils";
  }

  revision 2021-11-17 {
    description
      "Modified: default under cfp-configurations -> iosxr-default-ned-id";
  }

  revision 2021-11-09 {
    description
    "Removed: no-leafref-check for /te/tunnels/tunnel head-end and tail-end ";
  }

  revision 2021-05-24 {
    description
    "Commented out grouping for tunnel-protection-actions and tunnel-actions and te-action-result";
  }

  revision 2021-05-07 {
    description
    "Modified: augment te->tunnel-plan->plan to use tsdn-core-fp-common:status-code-plan-augmentation";
  }

  revision 2021-02-15 {
    description "Removed unused groupings
                 Modified default value for iosxr-default-ned-id to cisco-iosxr-cli-7.33";
  }
  revision 2021-02-04 {
    description "Added tailf:info for IETF config and updated ranges and description to support tooltip in UI";
  }

  revision 2020-12-11 {
    description "Modified default value for iosxr-default-ned-id to cisco-iosxr-cli-7.32";
  }

  revision 2020-12-01 {
    description "Added tailf:hidden full to te -> tunnels -> tunnel -> p2p-primary-paths ->
                 p2p-primary-path -> path-computation-server";
  }

  revision 2020-11-16 {
    description "Added validate callpoint to service";
  }

  revision 2020-11-10 {
    description "Added leaf sync-direction as mandatory input to error-recovery action";
  }

  revision "2020-11-04" {
    description "Added self-test action under te -> tunnels -> tunnel";
  }

  revision "2020-10-09" {
    description "Added grouing tunnel-steering-grouping for traffic-steering configs
                 under te -> tunnels -> tunnel";
  }

  revision "2020-09-21" {
    description "Moved internal-plan-change-handler and update-internal-fp-configurations
                  actions to a separate container ietf-te-actions";
  }
  revision "2020-08-18" {
    description "Removed device-te-node construct.
                 Added head-end and tail-end.";
  }

  revision "2020-08-10" {
    description "Added cleanup action.";
  }

  revision "2020-06-10" {
    description "Add NSO extention.";
  }

  revision "2019-04-09" {
    description "Latest update to TE generic YANG module.";
    reference
      "RFCXXXX: A YANG Data Model for Traffic Engineering Tunnels
       and Interfaces";
  }

  identity path-computation-error-reason {
    description
      "Base identity for path computation error reasons";
  }
  identity path-computation-error-no-topology {
    base path-computation-error-reason;
    description
      "Path computation error no topology error reason";
  }
  identity path-computation-error-no-server {
    base path-computation-error-reason;
    description
      "Path computation error no server error reason";
  }
  identity path-computation-error-path-not-found {
    base path-computation-error-reason;
    description
      "Path computation no path found error reason";
  }

  typedef tunnel-ref {
    type leafref {
      path "/te:te/te:tunnels/te:tunnel/te:name";
    }
    description
      "This type is used by data models that need to reference
       configured TE tunnel.";
  }
  // NSO-REMOVED START
  // typedef tunnel-p2mp-ref {
  //   type leafref {
  //     path "/te:te/te:tunnels/te:tunnel-p2mp/te:name";
  //   }
  //   description
  //     "This type is used by data models that need to reference
  //      configured P2MP TE tunnel.";
  //   reference "RFC4875";
  // }
  // NSO-REMOVED END

  typedef path-ref {
    // NSO-REMOVED START
    // type union {
    //   type leafref {
    //     path "/te:te/te:tunnels/te:tunnel/" +
    //           "te:p2p-primary-paths/te:p2p-primary-path/te:name";
    //   }
    //   type leafref {
    //     path "/te:te/te:tunnels/te:tunnel/" +
    //          "te:p2p-secondary-paths/te:p2p-secondary-path/te:name";
    //   }
    // }
    // NSO-REMOVED END
    type leafref {
      path "/te:te/te:tunnels/te:tunnel/" +
           "te:p2p-primary-paths/te:p2p-primary-path/te:name";
    }
    description
      "This type is used by data models that need to reference
       configured primary or secondary path of a TE tunnel.";
  }

  /**
   * TE tunnel generic groupings
   */
  // NSO-REMOVED START
  // grouping p2p-secondary-path-properties {
  //   description "tunnel path properties.";
  //   uses p2p-path-properties;
  //   uses path-constraints-common;
  //   uses protection-restoration-properties;
  //   uses p2p-path-properties-state;
  // }
  // NSO-REMOVED END

  grouping p2p-primary-path-properties {
    description
      "TE tunnel primary path properties grouping";
    uses p2p-path-properties;
    uses path-constraints-common;
    uses p2p-path-properties-state;
  }

  // NSO-REMOVED START
  // grouping path-properties {
  //   description "TE computed path properties grouping";
  //   container path-properties {
  //     tailf:info "The TE path computed properties";
  //     description "The TE path computed properties";
  //     list path-metric {
  //       key metric-type;
  //       tailf:info "TE path metric type";
  //       description "TE path metric type";
  //       leaf metric-type {
  //         type identityref {
  //           base te-types:path-metric-type;
  //         }
  //         tailf:info "TE path metric type";
  //         description "TE path metric type";
  //       }
  //       leaf accumulative-value {
  //         type uint64;
  //         tailf:info "TE path metric accumulative value";
  //         description "TE path metric accumulative value";
  //       }
  //     }
  //     uses te-types:generic-path-affinities;
  //     uses te-types:generic-path-srlgs;
  //     container path-route-objects {
  //       config 'false';
  //       description
  //         "Container for the list of computed route objects
  //          as returned by the computation engine";
  //       list path-computed-route-object {
  //         key index;
  //         ordered-by user;
  //         description
  //           "List of computed route objects returned by the
  //            computation engine";
  //         leaf index {
  //           type uint32;
  //           description
  //             "Route object entry index. The index is used to
  //              identify an entry in the list. The order of entries
  //              is defined by the user without relying on key values";
  //         }
  //         uses te-types:explicit-route-hop;
  //       }
  //     }
  //     uses shared-resources-tunnels;
  //   }
  // }
  // NSO-REMOVED END

  grouping p2p-path-properties-state {
    description "TE per path state parameters";
    // NSO-REMOVED START
    // container computed-paths-properties {
    //   config 'false';
    //   description "Computed path properties container";
    //   list computed-path-properties {
    //     key k-index;
    //     description "List of computed paths";
    //     leaf k-index {
    //       type uint8;
    //       description
    //         "The k-th path returned from the computation server.
    //          A lower k value path is more optimal than higher k
    //          value path(s)";
    //     }
    //     uses path-properties {
    //       description "The TE path computed properties";
    //     }
    //   }
    // }
    // NSO-REMOVED END
    uses computed-path-error-info;
    uses lsp-provisioning-error-info {
      // NSO-REMOVED START
      // augment "lsp-provisioning-error-infos/" +
      //         "lsp-provisioning-error-info" {
      //   description
      //     "Augmentation of LSP provisioning information under a
      //      specific path";
      //   leaf lsp-id {
      //     type uint16;
      //     description
      //       "The LSP-ID for which path compatutation was performed.";
      //   }
      // }
      // NSO-REMOVED END
    }
    // NSO-REMOVED START
    // container lsps {
    //   config 'false';
    //   description "TE LSPs container";
    //   list lsp {
    //     key "lsp-id";
    //     description "List of LSPs associated with the tunnel.";

    //     uses lsp-provisioning-error-info;
    //     uses lsp-properties-state;
    //     uses shared-resources-tunnels-state;
    //     uses lsp-record-route-information-state;
    //     uses path-properties {
    //       description "The TE path actual properties";
    //     }
    //   }
    // }
    // NSO-REMOVED END
  }

  grouping computed-path-error-info {
    description
      "Grouping for path computation error information";
    // NSO-REMOVED START
    // container computed-path-error-infos {
    //   config false;
    //   description
    //     "Path computation information container";
    //   list computed-path-error-info {
    //     description
    //       "List of path computation info entries";
    //     leaf error-description {
    //       type string;
    //       description
    //         "Textual representation of the error occurred during
    //          path compuation.";
    //     }
    //     leaf error-timestamp {
    //       type yang:date-and-time;
    //       description
    //         "Timestamp of last path computation attempt.";
    //     }
    //     leaf error-reason {
    //       type identityref {
    //         base path-computation-error-reason;
    //       }
    //       description
    //         "Reason for the path computation error.";
    //     }
    //   }
    // }
    // NSO-REMOVED END
  }

  grouping lsp-provisioning-error-info {
    description
      "Grouping for LSP provisioning error information";
    // NSO-REMOVED START
    // container lsp-provisioning-error-infos {
    //   config false;
    //   description
    //     "LSP provisioning error information";
    //   list lsp-provisioning-error-info {
    //     description
    //       "List of LSP provisioning error info entries";
    //     leaf error-description {
    //       type string;
    //       description
    //         "Textual representation of the error occurred during
    //          path compuation.";
    //     }
    //     leaf error-timestamp {
    //       type yang:date-and-time;
    //       description
    //         "Timestamp of when the reported error occurred.";
    //     }
    //     leaf error-node-id {
    //       type te-types:te-node-id;
    //       default "0.0.0.0";
    //       description
    //         "Node identifier of node where error occurred.";
    //     }
    //     leaf error-link-id {
    //       type te-types:te-tp-id;
    //       default 0;
    //       description
    //         "Link ID where the error occurred.";
    //     }
    //   }
    // }
    // NSO-REMOVED END
  }

  grouping p2p-path-properties-common {
    description
      "TE tunnel common path properties configuration grouping";
    leaf name {
      type string;
      tailf:info "TE path name";
      description "TE path name";
    }
    // NSO-REMOVED START
    // leaf path-setup-protocol {
    //   type identityref {
    //     base te-types:path-signaling-type;
    //   }
    //   default te-types:path-setup-static;
    //   tailf:info "Signaling protocol used to set up this tunnel";
    //   description
    //     "Signaling protocol used to set up this tunnel";
    // }
    // NSO-REMOVED END
    leaf path-computation-method {
      type identityref {
        base te-types:path-computation-method;
      }
      default te-types:path-locally-computed;
      tailf:info "The method used for computing the path, either
        locally computed, queried from a server or not
        computed at all (explicitly configured).";
      description
        "The method used for computing the path, either
        locally computed, queried from a server or not
        computed at all (explicitly configured).";
    }
    // NSO-REMOVED START
    // leaf path-computation-server {
    //   when "../path-computation-method = "+
    //   "'te-types:path-externally-queried'" {
    //     description
    //       "The path-computation server when the path is
    //        externally queried";
    //   }
    //   type inet:ip-address;
    //   tailf:info "Address of the external path computation
    //      server";
    //   description
    //     "Address of the external path computation
    //      server";
    // }
    // leaf compute-only {
    //   type empty;
    //   tailf:info "When set, the path is computed and updated whenever
    //      the topology is updated. No resources are committed
    //      or reserved in the network.";
    //   description
    //     "When set, the path is computed and updated whenever
    //      the topology is updated. No resources are committed
    //      or reserved in the network.";
    // }
    // leaf use-path-computation {
    //   when "../path-computation-method =" +
    //   " 'te-types:path-locally-computed'";
    //   type boolean;
    //   default 'true';
    //   tailf:info "A CSPF dynamically computed path";
    //   description "A CSPF dynamically computed path";
    // }
    // leaf lockdown {
    //   type empty;
    //   description
    //     "Indicates no reoptimization to be attempted for
    //      this path.";
    // }
    // leaf path-scope {
    //   type identityref {
    //     base te-types:path-scope-type;
    //   }
    //   default te-types:path-scope-end-to-end;
    //   config 'false';
    //   tailf:info "Path scope if segment or an end-to-end path";
    //   description "Path scope if segment or an end-to-end path";
    // }
    // NSO-REMOVED END
  }

  // NSO-REMOVED START
  // grouping p2p-reverse-path-properties {
  //   description
  //     "TE tunnel reverse path properties configuration
  //      grouping";
  //   uses p2p-path-properties-common;
  //   uses te-types:generic-path-optimization;
  //   leaf named-path-constraint {
  //     if-feature te-types:named-path-constraints;
  //     type leafref {
  //       path "../../../../../../globals/"
  //       + "named-path-constraints/named-path-constraint/"
  //       + "name";
  //     }
  //     tailf:info "Reference to a globally defined named path
  //       constraint set";
  //     description
  //       "Reference to a globally defined named path
  //       constraint set";
  //   }
  // }

  // grouping p2p-primary-reverse-path-properties {
  //   description "TE P2P tunnel primary reverse path properties.";
  //   reference "RFC7551";
  //   container p2p-primary-reverse-path {
  //     tailf:info "Tunnel reverse primary path properties";
  //     description "Tunnel reverse primary path properties";
  //     uses p2p-reverse-path-properties;
  //     uses path-constraints-common;
  //     uses p2p-path-properties-state;
  //     container p2p-secondary-reverse-path {
  //       tailf:info "Tunnel reverse primary path properties";
  //       description "Tunnel reverse secondary path properties";
  //       uses p2p-secondary-reverse-path-properties;
  //     }
  //   }
  // }
  // NSO-REMOVED END

  grouping p2p-path-properties {
    description
      "TE tunnel path properties configuration grouping";
    uses p2p-path-properties-common;
    uses te-types:generic-path-optimization;
    leaf preference {
      type uint8 {
        range "1..255";
      }
      default 1;
      tailf:info "Specifies a preference for this path. The lower the
        number higher the preference. Range <1-255>";
      description
        "Specifies a preference for this path. The lower the
        number higher the preference. Range <1-255>";
    }
    // NSO-REMOVED START
    // leaf k-requested-paths {
    //   type uint8;
    //   default 1;
    //   tailf:info "The number of k-shortest-paths  requested from the path
    //      computation server and returned sorted by its optimization
    //      objective";
    //   description
    //     "The number of k-shortest-paths  requested from the path
    //      computation server and returned sorted by its optimization
    //      objective";
    // }
    // leaf named-path-constraint {
    //   if-feature te-types:named-path-constraints;
    //   type leafref {
    //     path "../../../../../globals/"
    //     + "named-path-constraints/named-path-constraint/"
    //     + "name";
    //   }
    //   description
    //     "Reference to a globally defined named path
    //     constraint set";
    // }
    // NSO-REMOVED END
  }

  // NSO-REMOVED START
  // grouping hierarchical-link-properties {
  //   description
  //     "Hierarchical link grouping";
  //   reference "RFC4206";
  //   container hierarchical-link {
  //     description
  //       "Identifies a hierarchical link (in client layer)
  //        that this tunnel is associated with.";
  //     leaf local-te-node-id {
  //       type te-types:te-node-id;
  //       default "0.0.0.0";
  //       tailf:info "Local TE node identifier";
  //       description
  //         "Local TE node identifier";
  //     }
  //     leaf local-te-link-tp-id {
  //       type te-types:te-tp-id;
  //       default 0;
  //       tailf:info "Local TE link termination point identifier";
  //       description
  //         "Local TE link termination point identifier";
  //     }
  //     leaf remote-te-node-id {
  //       type te-types:te-node-id;
  //       default "0.0.0.0";
  //       tailf:info "Remote TE node identifier";
  //       description
  //         "Remote TE node identifier";
  //     }
  //     uses te-types:te-topology-identifier;
  //   }
  // }

  // grouping protection-restoration-properties-state {
  //   description
  //     "Protection parameters grouping";
  //   leaf lockout-of-normal {
  //     type boolean;
  //     default 'false';
  //     description
  //       "
  //         When set to 'True', it represents a lockout of normal
  //         traffic external command. When set to 'False', it
  //         represents a clear lockout of normal traffic external
  //         command. The lockout of normal traffic command applies
  //         to this Tunnel.
  //       ";
  //     reference "RFC4427";
  //   }
  //   leaf freeze {
  //     type boolean;
  //     default 'false';
  //     description
  //       "
  //         When set to 'True', it represents a freeze external
  //         command. When set to 'False', it represents a clear
  //         freeze external command. The freeze command command
  //         applies to all the Tunnels which are sharing the
  //         protection resources with this Tunnel.
  //       ";
  //     reference "RFC4427";
  //   }
  //   leaf lsp-protection-role {
  //     type enumeration {
  //       enum working {
  //         description
  //           "A working LSP must be a primary LSP whilst a protecting
  //            LSP can be either a primary or a secondary LSP. Also,
  //            known as protected LSPs when working LSPs are associated
  //            with protecting LSPs.";
  //       }
  //       enum protecting {
  //         description
  //           "A secondary LSP is an LSP that has been provisioned
  //            in the control plane only; e.g. resource allocation
  //            has not been committed at the data plane";
  //       }
  //     }
  //     default working;
  //     description "LSP role type";
  //     reference "RFC4872, section 4.2.1";
  //   }

  //   leaf lsp-protection-state {
  //     type identityref {
  //       base te-types:lsp-protection-state;
  //     }
  //     default te-types:normal;
  //     description
  //       "The state of the APS state machine controlling which
  //        tunnels is using the resources of the protecting LSP.";
  //   }
  //   leaf protection-group-ingress-node-id {
  //     type te-types:te-node-id;
  //     default "0.0.0.0";
  //     description
  //       "Indicates the te-node-id of the protection group
  //       ingress node when the APS state represents an extenal
  //       command (LoP, SF, MS) applied to it or a WTR timer
  //       running on it. If the external command is not applied to
  //       the ingress node or the WTR timer is not running on it,
  //       this attribute is not specified. A value 0.0.0.0 is used
  //       when the te-node-id of the protection group ingress node is
  //       unknown (e.g., because the ingress node is outside the scope
  //       of control of the server)";
  //   }
  //   leaf protection-group-egress-node-id {
  //     type te-types:te-node-id;
  //     default "0.0.0.0";
  //     description
  //       "Indicates the te-node-id of the protection group egress node
  //       when the APS state represents an extenal command (LoP, SF,
  //       MS) applied to it or a WTR timer running on it. If the
  //       external command is not applied to the ingress node or
  //       the WTR timer is not running on it, this attribute is not
  //       specified. A value 0.0.0.0 is used when the te-node-id of
  //       the protection group ingress node is unknown (e.g., because
  //       the ingress node is outside the scope of control of the
  //       server)";
  //   }
  // }

  // grouping protection-restoration-properties {
  //   description "Protection and restoration parameters";

  //   container protection {
  //     description "Protection parameters";
  //     leaf enable {
  //       type boolean;
  //       default 'false';
  //       description
  //         "A flag to specify if LSP protection is enabled";
  //       reference "RFC4427";
  //     }
  //     leaf protection-type {
  //       type identityref {
  //         base te-types:lsp-protection-type;
  //       }
  //       default te-types:lsp-protection-unprotected;
  //       description "LSP protection type.";
  //     }
  //     leaf protection-reversion-disable {
  //       type boolean;
  //       default 'false';
  //       description "Disable protection reversion to working path";
  //     }
  //     leaf hold-off-time {
  //       type uint32;
  //       units "milli-seconds";
  //       default 0;
  //       description
  //         "The time between the declaration of an SF or SD condition
  //          and the initialization of the protection switching
  //          algorithm.";
  //       reference "RFC4427";
  //     }
  //     leaf wait-to-revert {
  //       type uint16;
  //       units seconds;
  //       description
  //        "Time to wait before attempting LSP reversion";
  //       reference "RFC4427";
  //     }
  //     leaf aps-signal-id {
  //       type uint8 {
  //         range "1..255";
  //       }
  //       default 1;
  //       description
  //         "The APS signal number used to reference the traffic of this
  //          tunnel. The default value for normal traffic is 1.
  //          The default value for extra-traffic is 255. If not specified,
  //          non-default values can be assigned by the server,
  //          if and only if, the server controls both endpoints.";
  //       reference "RFC4427";
  //     }
  //   }
  //   container restoration {
  //     description "Restoration parameters";
  //     leaf enable {
  //       type boolean;
  //       default 'false';
  //       description
  //         "A flag to specify if LSP restoration is enabled";
  //       reference "RFC4427";
  //     }
  //     leaf restoration-type {
  //       type identityref {
  //         base te-types:lsp-restoration-type;
  //       }
  //       default te-types:lsp-restoration-restore-any;
  //       description "LSP restoration type.";
  //     }
  //     leaf restoration-scheme {
  //       type identityref {
  //         base te-types:restoration-scheme-type;
  //       }
  //       default te-types:restoration-scheme-preconfigured;
  //       description "LSP restoration scheme.";
  //     }
  //     leaf restoration-reversion-disable {
  //       type boolean;
  //       default 'false';
  //       description "Disable restoration reversion to working path";
  //     }
  //     leaf hold-off-time {
  //       type uint32;
  //       units "milli-seconds";
  //       description
  //         "The time between the declaration of an SF or SD condition
  //          and the initialization of the protection switching
  //          algorithm.";
  //       reference "RFC4427";
  //     }
  //     leaf wait-to-restore {
  //       type uint16;
  //       units seconds;
  //       description
  //         "Time to wait before attempting LSP restoration";
  //       reference "RFC4427";
  //     }
  //     leaf wait-to-revert {
  //       type uint16;
  //       units seconds;
  //       description
  //         "Time to wait before attempting LSP reversion";
  //       reference "RFC4427";
  //     }
  //   }
  // }

  // grouping p2p-dependency-tunnels-properties {
  //   description
  //     "Groupong for tunnel dependency list of tunnels";
  //   container dependency-tunnels {
  //     description "Dependency tunnels list";
  //     list dependency-tunnel {
  //       key "name";
  //       description "Dependency tunnel entry";
  //       leaf name {
  //         type leafref {
  //           path "../../../../../tunnels/tunnel/name";
  //           require-instance 'false';
  //         }
  //         description "Dependency tunnel name";
  //       }
  //       leaf encoding {
  //         type identityref {
  //           base te-types:lsp-encoding-types;
  //         }
  //         default te-types:lsp-encoding-packet;
  //         description "LSP encoding type";
  //         reference "RFC3945";
  //       }
  //       leaf switching-type {
  //         type identityref {
  //           base te-types:switching-capabilities;
  //         }
  //         default te-types:switching-psc1;
  //         description "LSP switching type";
  //         reference "RFC3945";
  //       }
  //     }
  //   }
  // }
  // NSO-REMOVED END

  grouping tunnel-p2p-config {
    description
      "Configuration parameters relating to TE tunnel";
    leaf name {
      // NSO MODIFICATION - START
      // Change type from string to string with pattern since this is the key of service
      type string {
        pattern '[\w\-\.:,_@#%$\+=\|;]+';
      }
      // NSO MODIFICATION - END
      tailf:info "TE tunnel name.";
      description "TE tunnel name.";
    }
    leaf identifier {
      type uint16;
      tailf:info
        "TE tunnel Identifier Range <0-65535> ";
      description
        "TE tunnel Identifier Range <0-65535> ";
      reference "RFC3209";
      //NSO MODIFICATION - START
      mandatory true;
      // NSO MODIFICATION - END
    }
    leaf description {
      type string;
      default 'None';
      tailf:info "Textual description for this TE tunnel";
      description
        "Textual description for this TE tunnel";
    }
    // NSO-REMOVED START
    // leaf encoding {
    //   type identityref {
    //     base te-types:lsp-encoding-types;
    //   }
    //   default te-types:lsp-encoding-packet;
    //   description "LSP encoding type";
    //   reference "RFC3945";
    // }
    // leaf switching-type {
    //   type identityref {
    //     base te-types:switching-capabilities;
    //   }
    //   default te-types:switching-psc1;
    //   description "LSP switching type";
    //   reference "RFC3945";
    // }
    // leaf provisioning-state {
    //   type identityref {
    //     base te-types:tunnel-state-type;
    //   }
    //   default te-types:tunnel-state-up;
    //   description "TE tunnel administrative state.";
    // }
    // leaf preference {
    //   type uint8 {
    //     range "1..255";
    //   }
    //   default 100;
    //   description
    //     "Specifies a preference for this tunnel.
    //      A lower number signifies a better preference";
    // }
    // leaf reoptimize-timer {
    //   type uint16;
    //   units seconds;
    //   description
    //    "frequency of reoptimization of a traffic engineered LSP";
    // }
    // NSO-REMOVED END

    leaf source {
      type te-types:te-node-id;
      tailf:info "TE tunnel source node ID.";
      description "TE tunnel source node ID.";
      //NSO MODIFICATION - START
      mandatory true;
      // NSO MODIFICATION - END
    }
    // NSO MODIFICATION - END
    leaf destination {
      type te-types:te-node-id;
      tailf:info "TE tunnel destination node ID";
      description "TE tunnel destination node ID";
      //NSO MODIFICATION - START
      mandatory true;
      // NSO MODIFICATION - END
    }
    // NSO-REMOVED START
    // leaf src-tp-id {
    //   type yang:hex-string;
    //   default '00:00:00:00';
    //   tailf:info "TE tunnel source termination point identifier.";
    //   description
    //     "TE tunnel source termination point identifier.";
    // }
    // leaf dst-tp-id {
    //   type yang:hex-string;
    //   default '00:00:00:00';
    //   tailf:info "TE tunnel destination termination point identifier.";
    //   description
    //     "TE tunnel destination termination point identifier.";
    // }
    // NSO-REMOVED END
    leaf bidirectional {
      type boolean;
      default 'false';
      tailf:info "TE tunnel bidirectional";
      description "TE tunnel bidirectional";
    }
    uses te-types:tunnel-constraints;
    // NSO-REMOVED START
    // uses tunnel-p2p-associations-properties;
    // uses protection-restoration-properties;
    // uses p2p-dependency-tunnels-properties;
    // uses hierarchical-link-properties;
    // NSO-REMOVED END
  }

  // NSO-REMOVED START
  // grouping tunnel-p2p-associations-properties {
  //   description "TE tunnel association grouping";
  //   container association-objects {
  //     description "TE tunnel associations";
  //     list association-object {
  //       key "type ID source global-source";
  //       description "List of association base objects";
  //       reference "RFC4872";
  //       leaf type {
  //         type identityref {
  //           base te-types:association-type;
  //         }
  //         description "Association type";
  //         reference "RFC4872";
  //       }
  //       leaf ID {
  //         type uint16;
  //         description "Association ID";
  //         reference "RFC4872";
  //       }
  //       leaf source {
  //         type te-types:te-node-id;
  //         description "Association source";
  //         reference "RFC4872";
  //       }
  //       leaf global-source {
  //         type te-types:te-node-id;
  //         description "Association global source";
  //         reference "RFC4872";
  //       }
  //     }
  //     list association-object-extended {
  //       key "type ID source global-source extended-ID";
  //       description "List of extended association objects";
  //       reference "RFC6780";
  //       leaf type {
  //         type identityref {
  //           base te-types:association-type;
  //         }
  //         description "Association type";
  //       }
  //       leaf ID {
  //         type uint16;
  //         description "Association ID";
  //         reference "RFC4872";
  //       }
  //       leaf source {
  //         type te-types:te-node-id;
  //         description "Association source";
  //       }
  //       leaf global-source {
  //         type te-types:te-node-id;
  //         description "Association global source";
  //         reference "RFC4872";
  //       }
  //       leaf extended-ID {
  //         type yang:hex-string;
  //         description "Association extended ID";
  //         reference "RFC4872";
  //       }
  //     }
  //   }
  // }

  // grouping path-access-segment-info {
  //   description
  //     "If an end-to-end tunnel crosses multiple domains using
  //      the same technology, some additional constraints have to be
  //      taken in consideration in each domain";
  //   container path-in-segment {
  //     presence
  //       "The end-to-end tunnel starts in a previous domain;
  //        this tunnel is a segment in the current domain.";
  //     description
  //       "This tunnel is a segment that needs to be coordinated
  //        with previous segment stitched on head-end side.";
  //     uses te-types:label-set-info;
  //   }
  //   container path-out-segment {
  //     presence
  //       "The end-to-end tunnel is not terminated in this domain;
  //        this tunnel is a segment in the current domain.";
  //     description
  //       "This tunnel is a segment that needs to be coordinated
  //        with previous segment stitched on head-end side.";
  //     uses te-types:label-set-info;
  //   }
  // }

  /* TE tunnel configuration/state grouping */
  // grouping tunnel-p2mp-properties {
  //   description
  //     "Top level grouping for P2MP tunnel properties.";
  //   leaf name {
  //     type string;
  //     description "TE tunnel name.";
  //   }
  //   leaf identifier {
  //     type uint16;
  //     description
  //       "TE tunnel Identifier.";
  //     reference "RFC3209";
  //   }
  //   leaf description {
  //     type string;
  //     default 'None';
  //     description
  //       "Textual description for this TE tunnel";
  //   }
  //   leaf operational-state {
  //     type identityref {
  //       base te-types:tunnel-state-type;
  //     }
  //     default te-types:tunnel-state-up;
  //     config 'false';
  //     description "TE tunnel administrative state.";
  //   }
  // }

  // grouping p2p-path-candidate-secondary-path-config {
  //   description
  //     "Configuration parameters relating to a secondary path which
  //     is a candidate for a particular primary path";

  //   leaf secondary-path {
  //     type leafref {
  //       path "../../../../../p2p-secondary-paths/" +
  //            "p2p-secondary-path/name";
  //     }
  //     description
  //       "A reference to the secondary path that should be utilised
  //       when the containing primary path option is in use";
  //   }

  //   leaf path-setup-protocol {
  //     type identityref {
  //       base te-types:path-signaling-type;
  //     }
  //     default te-types:path-setup-static;
  //     description
  //       "Signaling protocol used to set up this tunnel";
  //   }
  // }

  // grouping p2p-secondary-reverse-path-properties {
  //   description
  //     "Configuration parameters relating to a secondary path which
  //      is a candidate for a particular primary path";

  //   leaf secondary-path {
  //     type leafref {
  //       path "../../../../../p2p-secondary-paths/" +
  //            "p2p-secondary-path/name";
  //     }
  //     description
  //       "A reference to the secondary path that should be utilised
  //       when the containing primary path option is in use";
  //   }

  //   leaf path-setup-protocol {
  //     type identityref {
  //       base te-types:path-signaling-type;
  //     }
  //     default te-types:path-setup-static;
  //     description
  //       "Signaling protocol used to set up this tunnel";
  //   }
  // }
  // NSO-REMOVED END

  grouping tunnel-p2p-properties {
    description
      "Top level grouping for tunnel properties.";
    // NSO-REMOVED START
    // leaf operational-state {
    //   type identityref {
    //     base te-types:tunnel-state-type;
    //   }
    //   default te-types:tunnel-state-up;
    //   config 'false';
    //   description "TE tunnel administrative state.";
    // }
    // NSO-REMOVED END
    uses tunnel-p2p-config;
    container p2p-primary-paths {
      description "Set of P2P primary aths container";
      list p2p-primary-path {
        key "name";
        tailf:info "List of primary paths for this tunnel.";
        description
          "List of primary paths for this tunnel.";
        uses p2p-primary-path-properties;
        // NSO-REMOVED START
        // uses p2p-primary-reverse-path-properties;
        // container candidate-p2p-secondary-paths {
        //   description
        //     "The set of candidate secondary paths which may be used
        //     for this primary path. When secondary paths are specified
        //     in the list the path of the secondary LSP in use must be
        //     restricted to those path options referenced. The
        //     priority of the secondary paths is specified within the
        //     list. Higher priority values are less preferred - that is
        //     to say that a path with priority 0 is the most preferred
        //     path. In the case that the list is empty, any secondary
        //     path option may be utilised when the current primary path
        //     is in use.";
        //   list candidate-p2p-secondary-path {
        //     key "secondary-path";
        //     description
        //       "List of secondary paths for this tunnel.";
        //     uses p2p-path-candidate-secondary-path-config;

        //     leaf active {
        //       type boolean;
        //       config 'false';
        //       description
        //         "Indicates the current active path option that has
        //         been selected of the candidate secondary paths";
        //     }
        //   }
        // }
        // NSO-REMOVED END
      }
    }
  // NSO-REMOVED START
  //   container p2p-secondary-paths {
  //     description "Set of P2P secondary paths container";
  //     list p2p-secondary-path {
  //       key "name";
  //       description
  //         "List of secondary paths for this tunnel.";
  //       uses p2p-secondary-path-properties;
  //     }
  //   }
  // NSO-REMOVED END
  }

  // NSO-REMOVED START
  // grouping shared-resources-tunnels-state {
  //   description
  //     "The specific tunnel that is using the shared secondary path
  //      resources";
  //   leaf lsp-shared-resources-tunnel {
  //     type tunnel-ref;
  //     description
  //       "Reference to the tunnel that sharing secondary path
  //       resources with this tunnel";
  //   }
  // }

  // grouping shared-resources-tunnels {
  //   description
  //     "Set of tunnels that share secondary path resources with
  //     this tunnnel";
  //   container shared-resources-tunnels {
  //     description
  //       "Set of tunnels that share secondary path resources with
  //       this tunnnel";
  //     leaf-list lsp-shared-resources-tunnel {
  //       type tunnel-ref;
  //       description
  //         "Reference to the tunnel that sharing secondary path
  //         resources with this tunnel";
  //     }
  //   }
  // }
  // NSO-REMOVED END

  // NSO-REMOVED START
  // grouping tunnel-actions {
  //   description "Tunnel actions";
  //   action tunnel-action {
  //     description "Tunnel action";
  //     input {
  //       leaf action-type {
  //         type identityref {
  //           base te-types:tunnel-action-type;
  //         }
  //         description "Tunnel action type";
  //       }
  //     }
  //     output {
  //       leaf action-result {
  //         type identityref {
  //           base te-types:te-action-result;
  //         }
  //         description "The result of the RPC operation";
  //       }
  //     }
  //   }
  // }


  // grouping tunnel-protection-actions {
  //   description
  //     "Protection external command actions";
  //   action protection-external-commands {
  //     input {
  //       leaf protection-external-command {
  //         type identityref {
  //           base te-types:protection-external-commands;
  //         }
  //         description
  //           "Protection external command";
  //       }
  //       leaf protection-group-ingress-node-id {
  //         type te-types:te-node-id;
  //         description
  //           "When specified, indicates whether the action is
  //            applied on ingress node.
  //            By default, if neither ingress nor egress node-id
  //            is set, the the action applies to ingress node only.";
  //       }
  //       leaf protection-group-egress-node-id {
  //         type te-types:te-node-id;
  //         description
  //           "When specified, indicates whether the action is
  //            applied on egress node.
  //            By default, if neither ingress nor egress node-id
  //            is set, the the action applies to ingress node only.";
  //       }
  //       leaf path-ref {
  //         type path-ref;
  //         description
  //           "Indicates to which path the external command applies to.";
  //       }
  //       leaf traffic-type {
  //         type enumeration {
  //           enum normal-traffic {
  //             description
  //               "The manual-switch or forced-switch command applies to
  //                the normal traffic (this Tunnel).";
  //           }
  //           enum null-traffic {
  //             description
  //               "The manual-switch or forced-switch command applies to
  //                the null traffic.";
  //           }
  //           enum extra-traffic {
  //             description
  //               "The manual-switch or forced-switch command applies to
  //                the extra traffic (the extra-traffic Tunnel sharing
  //                protection bandwidth with this Tunnel).";
  //           }
  //         }
  //         description
  //           "Indicates whether the manual-switch or forced-switch
  //            commands applies to the normal traffic, the null traffic
  //            or the extra-traffic.";
  //         reference "RFC4427";
  //       }
  //       leaf extra-traffic-tunnel-ref {
  //         type tunnel-ref;
  //         description
  //           "In case there are multiple extra-traffic tunnels sharing
  //            protection bandwidth with this Tunnel (m:n protection),
  //            represents which extra-traffic Tunnel the manual-switch or
  //            forced-switch to extra-traffic command applies to.";
  //       }
  //     }
  //   }
  // }
  // NSO-REMOVED END

  /*** End of TE tunnel groupings ***/

  /**
   * LSP related generic groupings
   */
  // NSO-REMOVED START
  // grouping lsp-record-route-information-state {
  //   description "recorded route information grouping";
  //   container lsp-record-route-information {
  //     description "RSVP recorded route object information";
  //     list lsp-record-route-information {
  //       when "../../origin-type = 'ingress'" {
  //         description "Applicable on ingress LSPs only";
  //       }
  //       key "index";
  //       description "Record route list entry";
  //       uses te-types:record-route-state;
  //     }
  //   }
  // }
  // NSO-REMOVED END

  grouping lsps-state-grouping {
    description
      "LSPs state operational data grouping";
    // NSO-REMOVED START
    // container lsps-state {
    //   config 'false';
    //   description "TE LSPs state container";
    //   list lsp {
    //     key
    //       "source destination tunnel-id lsp-id "+
    //       "extended-tunnel-id";
    //     description "List of LSPs associated with the tunnel.";
    //     uses lsp-properties-state;
    //     uses lsp-record-route-information-state;
    //   }
    // }
    // NSO-REMOVED END
  }

  /*** End of TE LSP groupings ***/

  /**
   * TE global generic groupings
   */

  /* Global named admin-groups configuration data */
  // NSO-REMOVED START
  // grouping named-admin-groups-properties {
  //   description
  //     "Global named administrative groups configuration
  //     grouping";
  //   leaf name {
  //     type string;
  //     description
  //       "A string name that uniquely identifies a TE
  //       interface named admin-group";
  //   }
  //   leaf bit-position {
  //     type uint32;
  //     description
  //       "Bit position representing the administrative group";
  //     reference "RFC3209 and RFC7308";
  //   }
  // }

  // grouping named-admin-groups {
  //   description
  //     "Global named administrative groups configuration
  //     grouping";
  //   container named-admin-groups {
  //     description "TE named admin groups container";
  //     list named-admin-group {
  //       if-feature te-types:extended-admin-groups;
  //       if-feature te-types:named-extended-admin-groups;
  //       key "name";
  //       description
  //         "List of named TE admin-groups";
  //       uses named-admin-groups-properties;
  //     }
  //   }
  // }

  /* Global named admin-srlgs configuration data */
  // grouping named-srlgs-properties {
  //   description
  //     "Global named SRLGs configuration grouping";
  //   leaf name {
  //     type string;
  //     description
  //       "A string name that uniquely identifies a TE
  //       interface named srlg";
  //   }
  //   leaf group {
  //     type te-types:srlg;
  //     description "An SRLG value";
  //   }
  //   leaf cost {
  //     type uint32;
  //     description
  //       "SRLG associated cost. Used during path to append
  //        the path cost when traversing a link with this SRLG";
  //   }
  // }

  // grouping named-srlgs {
  //   description
  //     "Global named SRLGs configuration grouping";
  //   container named-srlgs {
  //     description "TE named SRLGs container";
  //     list named-srlg {
  //       if-feature te-types:named-srlg-groups;
  //       key "name";
  //       description
  //         "A list of named SRLG groups";
  //       uses named-srlgs-properties;
  //     }
  //   }
  // }

  /* Global named paths constraints configuration data */
  // grouping path-constraints-state {
  //   description "TE path constraints state";
  //   leaf bandwidth {
  //     type te-types:te-bandwidth;
  //     config 'false';
  //     description
  //       "A technology agnostic requested bandwidth to use
  //        for path computation";
  //   }
  //   leaf disjointness-type {
  //     type te-types:te-path-disjointness;
  //     config 'false';
  //     description
  //       "The type of resource disjointness.";
  //   }
  // }
  // NSO-REMOVED END

  grouping path-constraints-common {
    description
      "Global named path constraints configuration
       grouping";
    uses te-types:path-constraints-route-objects;
    // NSO-REMOVED START
    // uses te-types:common-path-constraints-attributes;
    // uses te-types:generic-path-disjointness;
    // NSO-REMOVED END
    // uses shared-resources-tunnels {
    //   description
    //     "Set of tunnels that are allowed to share secondary path
    //      resources of this tunnel";
    // }
    // uses path-access-segment-info {
    //   description
    //     "Tunnel constraints induced by other segments.";
    // }
    // NSO-REMOVED END
  }

  // NSO-REMOVED START
  // grouping named-path-constraints {
  //   description
  //     "Global named path constraints configuration
  //     grouping";
  //   container named-path-constraints {
  //     description "TE named path constraints container";
  //     list named-path-constraint {
  //       if-feature te-types:named-path-constraints;
  //       key "name";
  //       leaf name {
  //         type string;
  //         description
  //           "A string name that uniquely identifies a
  //           path constraint set";
  //       }
  //       uses path-constraints-common;
  //       description
  //         "A list of named path constraints";
  //     }
  //   }
  // }

  /* TE globals container data */
  // grouping globals-grouping {
  //   description
  //     "Globals TE system-wide configuration data grouping";
  //   container globals {
  //     description
  //       "Globals TE system-wide configuration data container";

  //     uses named-srlgs;
  //     uses named-admin-groups;
  //     uses named-path-constraints;
  //   }
  // }
  // NSO-REMOVED END

  /* TE tunnels container data */
  grouping tunnels-grouping {
    description
      "Tunnels TE configuration data grouping";
    container tunnels {
      tailf:info "Tunnels TE configuration data container";
      description
        "Tunnels TE configuration data container";

      list tunnel {
        key "name";

        // NSO ADDITION - START
        uses ncs:service-data;
        ncs:servicepoint ietf-te-tunnel-p2p;

        tailf:validate "ietf-te-validation" {
            tailf:dependency ".";
        }

        uses ct-hook:template-hook;
        // NSO ADDITION - END

        description "P2P TE tunnels list.";
        uses tunnel-p2p-properties;

        // NSO-REMOVED START
        // uses tunnel-actions;
        // uses tunnel-protection-actions;
        // NSO-REMOVED END

        // NSO MODIFICATION - START
        must "(bidirectional = 'false') or" +
             " ((bidirectional = 'true') and" +
             "  (current()/tail-end))" {
          error-message "Destination device (tail-end) must be provided in case of bidirectional tunnel.";
        }

        tailf:action error-recovery {
          tailf:actionpoint cisco-ietf-te-fp-service-error-recovery;
          tailf:info "Action to recover a service during create/update/delete from a transient failures
                      like device connection issues once the device is reachable again.
                      For create/update failures, this action issues a sync on the device
                      & redeploys the service with reconcile option.
                      For delete failures, this action issues a sync on the device &
                      redeploys zombie services.";
          description "Action to recover a service during create/update/delete from a transient failures
                      like device connection issues once the device is reachable again.
                      For create/update failures, this action issues a sync on the device
                      & redeploys the service with reconcile option.
                      For delete failures, this action issues a sync on the device &
                      redeploys zombie services.";
          input {
            leaf sync-direction {
              tailf:info "sync device with sync-from or sync-to";
              description "sync device with sync-from or sync-to";
              type enumeration {
                enum sync-from;
                enum sync-to;
              }
              mandatory true;
            }
            choice node-type {
              leaf source {
                tailf:info "Trigger error recovery for source";
                description "Trigger error recovery for source";
                type te-types:te-node-id;
              }
              leaf destination {
                tailf:info "Trigger error recovery for destination";
                description "Trigger error recovery for destination";
                type te-types:te-node-id;
              }
            }
          }
          output {
            leaf success {
              type boolean;
              mandatory true;
            }
            leaf detail {
              type string;
            }
          }
          tailf:confirm-text "########################\n" +
            "#        Warning       #\n" +
            "########################\n" +
            "You are about to recover a T-SDN service.\n" +
            "This will issue a sync on the device.\n" +
            "Are you sure you want to proceed?" {
              tailf:confirm-default false;
          }
        }
        container action {
          tailf:action self-test {
            tailf:actionpoint ietf-te-self-test-actionpoint;
            input {
            }
            output {
              leaf status {
                type string;
              }
              leaf message {
                type string;
              }
            }
          }
        }
        // NSO MODIFICATION - END
      }
      // NSO-REMOVED START
      // list tunnel-p2mp {
      //   key "name";
      //   unique "identifier";
      //   tailf:info "P2MP TE tunnels list.";
      //   description "P2MP TE tunnels list.";
      //   uses tunnel-p2mp-properties;
      // }
      // NSO-REMOVED END

      // NSO ADDITION - START
      list tunnel-plan {
        config false;
        tailf:cdb-oper {
          tailf:persistent true;
        }
        key "name";
        leaf name {
          type string;
        }

        uses ncs:nano-plan-data;
        uses ncs:nano-plan-history;
      }

      // these actions are to drive external plan in case of stacked-service
      container actions {

        tailf:action cleanup {
          tailf:actionpoint ietf-te-fp-cleanup;
          tailf:info "Clean up RSVP-TE service configuration and operational data";
          description "Clean up RSVP-TE service configuration and operational data";
          input {
            leaf service {
              type string;
              mandatory true;
            }
            leaf no-networking {
              type boolean;
              mandatory true;
            }
          }
          output {
            leaf success {
              type boolean;
              mandatory true;
            }
            leaf detail {
              type string;
            }
          }
          tailf:confirm-text "########################\n" +
            "#        Warning       #\n" +
            "########################\n" +
            "You are about to forcefully cleanup a T-SDN service.\n" +
            "This will affect the deploying service and leave network device(s) " +
            " & NSO out-of-sync (for no-networking=true).\n" +
            "Are you sure you want to proceed?" {
              tailf:confirm-default false;
          }
        }

        tailf:action error-recovery {
          tailf:actionpoint cisco-ietf-te-fp-error-recovery;
          tailf:info "Action to recover a service during create/update/delete from a transient failures
                      like device connection issues once the device is reachable again.
                      For create/update failures, this action issues a sync on the device
                      & redeploys the service with reconcile option.
                      For delete failures, this action issues a sync on the device &
                      redeploys zombie services.";
          description "Action to recover a service during create/update/delete from a transient failures
                      like device connection issues once the device is reachable again.
                      For create/update failures, this action issues a sync on the device
                      & redeploys the service with reconcile option.
                      For delete failures, this action issues a sync on the device &
                      redeploys zombie services.";
          input {
            leaf service {
              tailf:info "Service to recover";
              description "Service to recover";
              type string;
              mandatory true;
            }
            leaf sync-direction {
              tailf:info "sync device with sync-from or sync-to";
              description "sync device with sync-from or sync-to";
              type enumeration {
                enum sync-from;
                enum sync-to;
              }
              mandatory true;
            }
            choice node-type {
              leaf source {
                tailf:info "Trigger error recovery for source";
                description "Trigger error recovery for source";
                type te-types:te-node-id;
              }
              leaf destination {
                tailf:info "Trigger error recovery for destination";
                description "Trigger error recovery for destination";
                type te-types:te-node-id;
              }
            }
          }
          output {
            leaf success {
              type boolean;
              mandatory true;
            }
            leaf detail {
              type string;
            }
          }
          tailf:confirm-text "########################\n" +
            "#        Warning       #\n" +
            "########################\n" +
            "You are about to recover a T-SDN service.\n" +
            "This will issue a sync on the device.\n" +
            "Are you sure you want to proceed?" {
              tailf:confirm-default false;
          }
        }
      }
      // NSO ADDITION - END
    }
  }

  /* TE LSPs ephemeral state container data */
  // NSO-REMOVED START
  // grouping lsp-properties-state {
  //   description
  //     "LSPs state operational data grouping";
  //   leaf source {
  //     type te-types:te-node-id;
  //     description
  //       "Tunnel sender address extracted from
  //       SENDER_TEMPLATE  object";
  //     reference "RFC3209";
  //   }
  //   leaf destination {
  //     type te-types:te-node-id;
  //     description
  //       "Tunnel endpoint address extracted from
  //       SESSION object";
  //     reference "RFC3209";
  //   }
  //   leaf tunnel-id {
  //     type uint16;
  //     description
  //       "Tunnel identifier used in the SESSION
  //       that remains constant over the life
  //       of the tunnel.";
  //     reference "RFC3209";
  //   }
  //   leaf lsp-id {
  //     type uint16;
  //     description
  //       "Identifier used in the SENDER_TEMPLATE
  //       and the FILTER_SPEC that can be changed
  //       to allow a sender to share resources with
  //       itself.";
  //     reference "RFC3209";
  //   }
  //   leaf extended-tunnel-id {
  //     type yang:dotted-quad;
  //      description
  //       "Extended Tunnel ID of the LSP.";
  //     reference "RFC3209";
  //   }
  //   leaf operational-state {
  //     type identityref {
  //       base te-types:lsp-state-type;
  //     }
  //     description "LSP operational state.";
  //   }
  //   leaf path-setup-protocol {
  //     type identityref {
  //       base te-types:path-signaling-type;
  //     }
  //     default te-types:path-setup-static;
  //     description
  //       "Signaling protocol used to set up this tunnel";
  //   }
  //   leaf origin-type {
  //     type enumeration {
  //       enum ingress {
  //         description
  //           "Origin ingress";
  //       }
  //       enum egress {
  //         description
  //           "Origin egress";
  //       }
  //       enum transit {
  //         description
  //           "transit";
  //       }
  //     }
  //     default 'ingress';
  //     description
  //       "Origin type of LSP relative to the location
  //       of the local switch in the path.";
  //   }

  //   leaf lsp-resource-status {
  //     type enumeration {
  //       enum primary {
  //         description
  //           "A primary LSP is a fully established LSP for
  //            which the resource allocation has been committed
  //            at the data plane";
  //       }
  //       enum secondary {
  //         description
  //           "A secondary LSP is an LSP that has been provisioned
  //            in the control plane only; e.g. resource allocation
  //            has not been committed at the data plane";
  //       }
  //     }
  //     default 'primary';
  //     description "LSP resource allocation type";
  //     reference "RFC4872, section 4.2.1";
  //   }

  //   uses protection-restoration-properties-state;
  // }
  // NSO-REMOVED END
  /*** End of TE global groupings ***/

  /**
   * TE configurations container
   */
  container te {
    presence "Enable TE feature.";
    description
       "TE global container.";

    /* TE Global Configuration Data */
    // NSO-REMOVED START
    // uses globals-grouping;
    // NSO-REMOVED END

    /* TE Tunnel Configuration Data */
    uses tunnels-grouping;

    /* TE LSPs State Data */
    uses lsps-state-grouping;

  }

  /* TE Global RPCs/execution Data */
  rpc globals-rpc {
    description
      "Execution data for TE global.";
  }

  /* TE interfaces RPCs/execution Data */
  rpc interfaces-rpc {
    description
      "Execution data for TE interfaces.";
  }

  /* TE Tunnel RPCs/execution Data */
  // NSO-REMOVED START
  // rpc tunnels-rpc {
  //   description "TE tunnels RPC nodes";
  //   input {
  //     container tunnel-info {
  //       description "Tunnel Identification";
  //       choice type {
  //         description "Tunnel information type";
  //         case tunnel-p2p {
  //           leaf p2p-id {
  //             type tunnel-ref;
  //             description "P2P TE tunnel";
  //           }
  //         }
  //         case tunnel-p2mp {
  //           leaf p2mp-id {
  //             type tunnel-p2mp-ref;
  //             description "P2MP TE tunnel";
  //           }
  //         }
  //       }
  //     }
  //   }
  //   output {
  //     container result {
  //       description
  //         "The container result of the RPC operation";
  //       leaf result {
  //         type enumeration {
  //           enum success {
  //             description "Origin ingress";
  //           }
  //           enum in-progress {
  //             description "Origin egress";
  //           }
  //           enum fail {
  //             description "transit";
  //           }
  //         }
  //         description "The result of the RPC operation";
  //       }
  //     }
  //   }
  // }
  // NSO-REMOVED END

  /* TE Global Notification Data */
  notification globals-notif {
    description
      "Notification messages for Global TE.";
  }

  /* TE Tunnel Notification Data */
  notification tunnels-notif {
    description
      "Notification messages for TE tunnels.";
  }

  // NSO ADDITION - START
  // NSO-REMOVED START
  // grouping status-code-oper {
  //   leaf status-code-name {
  //       type string;
  //   }
  //   list status-context {
  //     key context-name;
  //     leaf context-name {
  //       type string;
  //     }
  //     leaf context-msg {
  //       type string;
  //     }
  //     list status-state {
  //       key state;
  //       leaf state {
  //         type string;
  //       }
  //       leaf value {
  //         type string;
  //       }
  //     }
  //   }
  // }
  // NSO-REMOVED END

  augment /te/tunnels/tunnel-plan/plan {
    uses tsdn-core-fp-common:status-code-plan-augmentation;
  }

  augment /te/tunnels/tunnel-plan/plan-history {
    uses tsdn-core-fp-common:status-code-plan-augmentation;
  }

  augment /te/tunnels/tunnel-plan/plan/component {
    uses tsdn-core-fp-common:status-code-component-augmentation;
  }

  augment /te/tunnels/tunnel-plan/plan-history/plan/component {
    uses tsdn-core-fp-common:status-code-component-augmentation;
  }

  augment /te/tunnels/tunnel {
    leaf head-end {
      tailf:info "Source device name.";
      description "Source device name.";
      type leafref {
        path "/ncs:devices/lsa-utils:lsa/lsa-utils:dispatch-map/lsa-utils:device/lsa-utils:name";
      }
      mandatory true;
    }
    leaf tail-end {
      tailf:info "Destination device name.";
      description "Destination device name.";
      type leafref {
        path "/ncs:devices/lsa-utils:lsa/lsa-utils:dispatch-map/lsa-utils:device/lsa-utils:name";
      }
    }

    uses tunnel-steering-grouping;
  }

  container ietf-te-actions {
    tailf:hidden tsdn;
    tailf:action internal-plan-change-handler {
      tailf:hidden full;
      tailf:actionpoint ietf-te-internal-plan-change-handler;
      input {
        uses kicker:action-input-params;
      }
      output {
      }
    }
    tailf:action update-internal-fp-configurations {
      tailf:hidden tsdn;
      tailf:actionpoint ietf-te-internal-fp-configurations;
      tailf:info "Copy over changes in external fp-configurations to internal fp-configurations";
      description "Copy over changes in external fp-configurations to internal fp-configurations";
      input {
      }
      output {
      }
    }
  }

  container cfp-configurations {
    list dynamic-device-mapping {
      tailf:info "Dynamic Device Mapping";
      description "Dynamic Device Mapping";
      key "ned-id";
      leaf ned-id {
        tailf:info "Device NED ID, eg ned:netconf";
        description "Device NED ID, eg ned:netconf";
        type string;
        tailf:cli-allow-range;
      }
      leaf python-impl-class-name {
        tailf:info "Device Python implementation class, eg module.class";
        description "Device Python implementation class, eg module.class";
        type string;
        mandatory true;
      }
    }

    leaf iosxr-default-ned-id {
      tailf:info "NED ID of the default IOSXR Device.";
      description "NED ID of the default IOSXR Device.";
      tailf:hidden tsdn;
      type string;
      default "cisco-iosxr-cli-7.40:cisco-iosxr-cli-7.40";
    }
  }

  grouping tunnel-steering-grouping {
    container traffic-steering {
      tailf:info "Steer traffic traffic through the tunnel";
      description  "Steer traffic traffic through the tunnel";
      choice steering-choice {
        // interface tunnel-te* / autoroute
        default autoroute;
        case autoroute {
          container autoroute {
            tailf:info "Parameters for IGP routing over tunnel";
            description "Parameters for IGP routing over tunnel";

            // interface tunnel-te* / autoroute announce
            container announce {
              tailf:info "Announce tunnel to IGP";
              description "Announce tunnel to IGP";

              leaf enable{
                tailf:info "Enable autoroute announce";
                description "Enable autoroute announce";
                type boolean;
                default 'true';
              }
              // interface tunnel-te* / autoroute announce / metric
              container metric {
                presence true;
                tailf:info "Specify MPLS tunnel metric";
                description "Specify MPLS tunnel metric";
                choice metric-choice {
                  // interface tunnel-te* / autoroute announce / metric constant
                  leaf constant {
                    tailf:info "<1-2147483647> - Set constant metric";
                    description "<1-2147483647> - Set constant metric";
                    type uint32 {
                      range "1..2147483647";
                    }
                  }
                  // interface tunnel-te* / autoroute announce / metric absolute
                  leaf absolute {
                    tailf:info "<1-2147483647> - Set absolute metric";
                    description "<1-2147483647> - Set absolute metric";
                    type uint32 {
                      range "1..2147483647";
                    }
                  }
                  // interface tunnel-te* / autoroute announce / metric relative
                  leaf relative {
                    tailf:info "<-10,+10> - Set relative metric";
                    description "<-10,+10> - Set relative metric";
                    type int8 {
                      range "-10..10";
                    }
                  }
                }
              }
            }

            // interface tunnel-te* / autoroute destination *
            list destination {
              tailf:info "Adds static route address A.B.C.D to destination";
              description "Adds static route address A.B.C.D to destination";
              key address;
              leaf address {
                tailf:info "A.B.C.D - IPv4 Address of static route to add";
                description "A.B.C.D - IPv4 Address of static route to add";
                type inet:ipv4-address;
              }
            }
          }
        }
        // interface tunnel-te* / forwarding-adjacency
         case forwarding-adjacency {
          container forwarding-adjacency {
            presence "true";
            tailf:info "Enable tunnel as a forwarding-adjacency";
            description "Enable tunnel as a forwarding-adjacency";

            // interface tunnel-te* / forwarding-adjacency / holdtime
            leaf holdtime {
              tailf:info "<0-20000> - Hold time in ms";
              description "<0-20000> - Hold time in ms";
              type uint16 {
                range "0..20000";
              }
            }

            // interface tunnel-te* / forwarding-adjacency / include-ipv6
            leaf include-ipv6 {
              tailf:info "Announce tunnel as an IPv6 FA also";
              description "Announce tunnel as an IPv6 FA also";
              type empty;
            }
          }
        }
      }
    }
  }
  // NSO ADDITION - END
}
