module cisco-zr-cfp-nano-plan-services {
  yang-version 1.1;

  namespace "http://cisco.com/ns/nso/cfp/cisco-zr-cfp-nano-plan-services";
  prefix cisco-zr-cfp-nano-plan-services;

  import tailf-common { prefix tailf; }
  import tailf-ncs { prefix ncs; }

  import cisco-zr-cfp {prefix cisco-zr-cfp; }

  revision 2020-12-06 {
    description "Initial version";
  }

  identity router {
    base ncs:plan-component-type;
  }

  identity config-apply {
    base ncs:plan-state;
  }

  ncs:plan-outline dco-nano-plan {
    ncs:component-type "ncs:self" {
      ncs:state "ncs:init";

      ncs:state "cisco-zr-cfp-nano-plan-services:config-apply" {
        ncs:create {
          // this applies config on device
          ncs:nano-callback;
        }
      }

      ncs:state "ncs:ready" {
        ncs:create {
          // mark state as failed in case device transaction is invalidated
          // this is needed due to CQ, where in device's last-transaction-id is set to INVALIDATED
          // in case of CQ failures. During redeploy's we do not want the service to go to 'reached'
          // state unless the device transaction is fixed.
          ncs:nano-callback;
        }
      }
    }
  }

  ncs:service-behavior-tree cisco-zr-dco-servicepoint {
    ncs:plan-outline-ref "cisco-zr-cfp-nano-plan-services:dco-nano-plan";
    ncs:plan-location "/cisco-zr-cfp:zr/cisco-zr-cfp:dco-plan";

    ncs:selector {
      ncs:variable "NAME" {
        ncs:value-expr "name";
      }
      ncs:variable "ROUTER" {
        ncs:value-expr "router";
      }

      ncs:create-component "'self'" {
        ncs:component-type-ref "ncs:self";
      }
    }
  }
}
